FME workspace gaugeReader.fmw

Parameters:
- watershed = 01   # Watershed number

Readers:
- GML_1: GML from https://waterservices.usgs.gov/nwis/iv/?format=waterml,2.0&parameterCd=00060&siteType=ST&period=PT1H&siteStatus=all&huc=$(watershed)

Writers:
- POSTGIS_1: POSTGIS to flowdb

MeasurementTimeseries (reader GML_1)
    attributes: metadata.owns xml_boolean, metadata.MeasurementTimeseriesMetadata.temporalExtent.nilReason xml_buffer, metadata.MeasurementTimeseriesMetadata.temporalExtent.gml_remoteSchema xml_buffer, metadata.MeasurementTimeseriesMetadata.temporalExtent.xlink_href xml_buffer, metadata.MeasurementTimeseriesMetadata.temporalExtent.xlink_title xml_buffer, metadata.MeasurementTimeseriesMetadata.temporalExtent.owns xml_boolean, metadata.MeasurementTimeseriesMetadata.temporalExtent.gml_TimePeriod.frame xml_buffer, metadata.MeasurementTimeseriesMetadata.temporalExtent.gml_TimePeriod.gml_id xml_buffer, metadata.MeasurementTimeseriesMetadata.temporalExtent.gml_TimePeriod.gml_relatedTime{} xml_xml, metadata.MeasurementTimeseriesMetadata.temporalExtent.gml_TimePeriod.gml_beginPosition xml_buffer, metadata.MeasurementTimeseriesMetadata.temporalExtent.gml_TimePeriod.gml_beginPosition.frame xml_buffer, metadata.MeasurementTimeseriesMetadata.temporalExtent.gml_TimePeriod.gml_beginPosition.calendarEraName xml_buffer, metadata.MeasurementTimeseriesMetadata.temporalExtent.gml_TimePeriod.gml_beginPosition.indeterminatePosition xml_char(7), metadata.MeasurementTimeseriesMetadata.temporalExtent.gml_TimePeriod.gml_begin.nilReason xml_buffer, metadata.MeasurementTimeseriesMetadata.temporalExtent.gml_TimePeriod.gml_begin.gml_remoteSchema xml_buffer, metadata.MeasurementTimeseriesMetadata.temporalExtent.gml_TimePeriod.gml_begin.xlink_href xml_buffer, metadata.MeasurementTimeseriesMetadata.temporalExtent.gml_TimePeriod.gml_begin.xlink_title xml_buffer, metadata.MeasurementTimeseriesMetadata.temporalExtent.gml_TimePeriod.gml_begin.owns xml_boolean, metadata.MeasurementTimeseriesMetadata.temporalExtent.gml_TimePeriod.gml_begin.gml_TimeInstant.frame xml_buffer, metadata.MeasurementTimeseriesMetadata.temporalExtent.gml_TimePeriod.gml_begin.gml_TimeInstant.gml_id xml_buffer, metadata.MeasurementTimeseriesMetadata.temporalExtent.gml_TimePeriod.gml_begin.gml_TimeInstant.gml_relatedTime{} xml_xml, metadata.MeasurementTimeseriesMetadata.temporalExtent.gml_TimePeriod.gml_begin.gml_TimeInstant.gml_timePosition xml_buffer, metadata.MeasurementTimeseriesMetadata.temporalExtent.gml_TimePeriod.gml_begin.gml_TimeInstant.gml_timePosition.frame xml_buffer, metadata.MeasurementTimeseriesMetadata.temporalExtent.gml_TimePeriod.gml_begin.gml_TimeInstant.gml_timePosition.calendarEraName xml_buffer, metadata.MeasurementTimeseriesMetadata.temporalExtent.gml_TimePeriod.gml_begin.gml_TimeInstant.gml_timePosition.indeterminatePosition xml_char(7), metadata.MeasurementTimeseriesMetadata.temporalExtent.gml_TimePeriod.gml_endPosition xml_buffer, metadata.MeasurementTimeseriesMetadata.temporalExtent.gml_TimePeriod.gml_endPosition.frame xml_buffer, metadata.MeasurementTimeseriesMetadata.temporalExtent.gml_TimePeriod.gml_endPosition.calendarEraName xml_buffer, metadata.MeasurementTimeseriesMetadata.temporalExtent.gml_TimePeriod.gml_endPosition.indeterminatePosition xml_char(7), metadata.MeasurementTimeseriesMetadata.temporalExtent.gml_TimePeriod.gml_end.nilReason xml_buffer,
      metadata.MeasurementTimeseriesMetadata.temporalExtent.gml_TimePeriod.gml_end.gml_remoteSchema xml_buffer, metadata.MeasurementTimeseriesMetadata.temporalExtent.gml_TimePeriod.gml_end.xlink_href xml_buffer, metadata.MeasurementTimeseriesMetadata.temporalExtent.gml_TimePeriod.gml_end.xlink_title xml_buffer, metadata.MeasurementTimeseriesMetadata.temporalExtent.gml_TimePeriod.gml_end.owns xml_boolean, metadata.MeasurementTimeseriesMetadata.temporalExtent.gml_TimePeriod.gml_end.gml_TimeInstant.frame xml_buffer, metadata.MeasurementTimeseriesMetadata.temporalExtent.gml_TimePeriod.gml_end.gml_TimeInstant.gml_id xml_buffer, metadata.MeasurementTimeseriesMetadata.temporalExtent.gml_TimePeriod.gml_end.gml_TimeInstant.gml_relatedTime{} xml_xml, metadata.MeasurementTimeseriesMetadata.temporalExtent.gml_TimePeriod.gml_end.gml_TimeInstant.gml_timePosition xml_buffer, metadata.MeasurementTimeseriesMetadata.temporalExtent.gml_TimePeriod.gml_end.gml_TimeInstant.gml_timePosition.frame xml_buffer, metadata.MeasurementTimeseriesMetadata.temporalExtent.gml_TimePeriod.gml_end.gml_TimeInstant.gml_timePosition.calendarEraName xml_buffer, metadata.MeasurementTimeseriesMetadata.temporalExtent.gml_TimePeriod.gml_end.gml_TimeInstant.gml_timePosition.indeterminatePosition xml_char(7), metadata.MeasurementTimeseriesMetadata.temporalExtent.gml_TimePeriod.gml_duration xml_buffer, metadata.MeasurementTimeseriesMetadata.temporalExtent.gml_TimePeriod.gml_timeInterval xml_real64, metadata.MeasurementTimeseriesMetadata.temporalExtent.gml_TimePeriod.gml_timeInterval.unit xml_buffer, metadata.MeasurementTimeseriesMetadata.temporalExtent.gml_TimePeriod.gml_timeInterval.radix xml_uint64, metadata.MeasurementTimeseriesMetadata.temporalExtent.gml_TimePeriod.gml_timeInterval.factor xml_int64, metadata.MeasurementTimeseriesMetadata.baseTime xml_buffer, metadata.MeasurementTimeseriesMetadata.baseTime.frame xml_buffer, metadata.MeasurementTimeseriesMetadata.baseTime.calendarEraName xml_buffer, metadata.MeasurementTimeseriesMetadata.baseTime.indeterminatePosition xml_char(7), metadata.MeasurementTimeseriesMetadata.spacing xml_buffer, metadata.MeasurementTimeseriesMetadata.commentBlock{}.owns xml_boolean, metadata.MeasurementTimeseriesMetadata.commentBlock{}.CommentBlock.applicablePeriod.nilReason xml_buffer, metadata.MeasurementTimeseriesMetadata.commentBlock{}.CommentBlock.applicablePeriod.gml_remoteSchema xml_buffer, metadata.MeasurementTimeseriesMetadata.commentBlock{}.CommentBlock.applicablePeriod.xlink_href xml_buffer, metadata.MeasurementTimeseriesMetadata.commentBlock{}.CommentBlock.applicablePeriod.xlink_title xml_buffer, metadata.MeasurementTimeseriesMetadata.commentBlock{}.CommentBlock.applicablePeriod.owns xml_boolean, metadata.MeasurementTimeseriesMetadata.commentBlock{}.CommentBlock.applicablePeriod.gml_TimePeriod.frame xml_buffer, metadata.MeasurementTimeseriesMetadata.commentBlock{}.CommentBlock.applicablePeriod.gml_TimePeriod.gml_id xml_buffer, metadata.MeasurementTimeseriesMetadata.commentBlock{}.CommentBlock.applicablePeriod.gml_TimePeriod.gml_relatedTime{} xml_xml,
      metadata.MeasurementTimeseriesMetadata.commentBlock{}.CommentBlock.applicablePeriod.gml_TimePeriod.gml_beginPosition xml_buffer, metadata.MeasurementTimeseriesMetadata.commentBlock{}.CommentBlock.applicablePeriod.gml_TimePeriod.gml_beginPosition.frame xml_buffer, metadata.MeasurementTimeseriesMetadata.commentBlock{}.CommentBlock.applicablePeriod.gml_TimePeriod.gml_beginPosition.calendarEraName xml_buffer, metadata.MeasurementTimeseriesMetadata.commentBlock{}.CommentBlock.applicablePeriod.gml_TimePeriod.gml_beginPosition.indeterminatePosition xml_char(7), metadata.MeasurementTimeseriesMetadata.commentBlock{}.CommentBlock.applicablePeriod.gml_TimePeriod.gml_begin.nilReason xml_buffer, metadata.MeasurementTimeseriesMetadata.commentBlock{}.CommentBlock.applicablePeriod.gml_TimePeriod.gml_begin.gml_remoteSchema xml_buffer, metadata.MeasurementTimeseriesMetadata.commentBlock{}.CommentBlock.applicablePeriod.gml_TimePeriod.gml_begin.xlink_href xml_buffer, metadata.MeasurementTimeseriesMetadata.commentBlock{}.CommentBlock.applicablePeriod.gml_TimePeriod.gml_begin.xlink_title xml_buffer, metadata.MeasurementTimeseriesMetadata.commentBlock{}.CommentBlock.applicablePeriod.gml_TimePeriod.gml_begin.owns xml_boolean, metadata.MeasurementTimeseriesMetadata.commentBlock{}.CommentBlock.applicablePeriod.gml_TimePeriod.gml_begin.gml_TimeInstant.frame xml_buffer, metadata.MeasurementTimeseriesMetadata.commentBlock{}.CommentBlock.applicablePeriod.gml_TimePeriod.gml_begin.gml_TimeInstant.gml_id xml_buffer, metadata.MeasurementTimeseriesMetadata.commentBlock{}.CommentBlock.applicablePeriod.gml_TimePeriod.gml_begin.gml_TimeInstant.gml_relatedTime{} xml_xml, metadata.MeasurementTimeseriesMetadata.commentBlock{}.CommentBlock.applicablePeriod.gml_TimePeriod.gml_begin.gml_TimeInstant.gml_timePosition xml_buffer, metadata.MeasurementTimeseriesMetadata.commentBlock{}.CommentBlock.applicablePeriod.gml_TimePeriod.gml_begin.gml_TimeInstant.gml_timePosition.frame xml_buffer, metadata.MeasurementTimeseriesMetadata.commentBlock{}.CommentBlock.applicablePeriod.gml_TimePeriod.gml_begin.gml_TimeInstant.gml_timePosition.calendarEraName xml_buffer, metadata.MeasurementTimeseriesMetadata.commentBlock{}.CommentBlock.applicablePeriod.gml_TimePeriod.gml_begin.gml_TimeInstant.gml_timePosition.indeterminatePosition xml_char(7), metadata.MeasurementTimeseriesMetadata.commentBlock{}.CommentBlock.applicablePeriod.gml_TimePeriod.gml_endPosition xml_buffer, metadata.MeasurementTimeseriesMetadata.commentBlock{}.CommentBlock.applicablePeriod.gml_TimePeriod.gml_endPosition.frame xml_buffer, metadata.MeasurementTimeseriesMetadata.commentBlock{}.CommentBlock.applicablePeriod.gml_TimePeriod.gml_endPosition.calendarEraName xml_buffer, metadata.MeasurementTimeseriesMetadata.commentBlock{}.CommentBlock.applicablePeriod.gml_TimePeriod.gml_endPosition.indeterminatePosition xml_char(7), metadata.MeasurementTimeseriesMetadata.commentBlock{}.CommentBlock.applicablePeriod.gml_TimePeriod.gml_end.nilReason xml_buffer, metadata.MeasurementTimeseriesMetadata.commentBlock{}.CommentBlock.applicablePeriod.gml_TimePeriod.gml_end.gml_remoteSchema xml_buffer, metadata.MeasurementTimeseriesMetadata.commentBlock{}.CommentBlock.applicablePeriod.gml_TimePeriod.gml_end.xlink_href xml_buffer, metadata.MeasurementTimeseriesMetadata.commentBlock{}.CommentBlock.applicablePeriod.gml_TimePeriod.gml_end.xlink_title xml_buffer, metadata.MeasurementTimeseriesMetadata.commentBlock{}.CommentBlock.applicablePeriod.gml_TimePeriod.gml_end.owns xml_boolean, metadata.MeasurementTimeseriesMetadata.commentBlock{}.CommentBlock.applicablePeriod.gml_TimePeriod.gml_end.gml_TimeInstant.frame xml_buffer, metadata.MeasurementTimeseriesMetadata.commentBlock{}.CommentBlock.applicablePeriod.gml_TimePeriod.gml_end.gml_TimeInstant.gml_id xml_buffer, metadata.MeasurementTimeseriesMetadata.commentBlock{}.CommentBlock.applicablePeriod.gml_TimePeriod.gml_end.gml_TimeInstant.gml_relatedTime{} xml_xml, metadata.MeasurementTimeseriesMetadata.commentBlock{}.CommentBlock.applicablePeriod.gml_TimePeriod.gml_end.gml_TimeInstant.gml_timePosition xml_buffer, metadata.MeasurementTimeseriesMetadata.commentBlock{}.CommentBlock.applicablePeriod.gml_TimePeriod.gml_end.gml_TimeInstant.gml_timePosition.frame xml_buffer,
      metadata.MeasurementTimeseriesMetadata.commentBlock{}.CommentBlock.applicablePeriod.gml_TimePeriod.gml_end.gml_TimeInstant.gml_timePosition.calendarEraName xml_buffer, metadata.MeasurementTimeseriesMetadata.commentBlock{}.CommentBlock.applicablePeriod.gml_TimePeriod.gml_end.gml_TimeInstant.gml_timePosition.indeterminatePosition xml_char(7), metadata.MeasurementTimeseriesMetadata.commentBlock{}.CommentBlock.applicablePeriod.gml_TimePeriod.gml_duration xml_buffer, metadata.MeasurementTimeseriesMetadata.commentBlock{}.CommentBlock.applicablePeriod.gml_TimePeriod.gml_timeInterval xml_real64, metadata.MeasurementTimeseriesMetadata.commentBlock{}.CommentBlock.applicablePeriod.gml_TimePeriod.gml_timeInterval.unit xml_buffer, metadata.MeasurementTimeseriesMetadata.commentBlock{}.CommentBlock.applicablePeriod.gml_TimePeriod.gml_timeInterval.radix xml_uint64, metadata.MeasurementTimeseriesMetadata.commentBlock{}.CommentBlock.applicablePeriod.gml_TimePeriod.gml_timeInterval.factor xml_int64, metadata.MeasurementTimeseriesMetadata.commentBlock{}.CommentBlock.comment xml_buffer, metadata.MeasurementTimeseriesMetadata.parameter{}.nilReason xml_buffer, metadata.MeasurementTimeseriesMetadata.parameter{}.gml_remoteSchema xml_buffer, metadata.MeasurementTimeseriesMetadata.parameter{}.xlink_href xml_buffer, metadata.MeasurementTimeseriesMetadata.parameter{}.xlink_title xml_buffer, metadata.MeasurementTimeseriesMetadata.parameter{}.NamedValue.name.owns xml_boolean, metadata.MeasurementTimeseriesMetadata.parameter{}.NamedValue.name.nilReason xml_buffer, metadata.MeasurementTimeseriesMetadata.parameter{}.NamedValue.name.gml_remoteSchema xml_buffer, metadata.MeasurementTimeseriesMetadata.parameter{}.NamedValue.name.xlink_href xml_buffer, metadata.MeasurementTimeseriesMetadata.parameter{}.NamedValue.name.xlink_title xml_buffer, metadata.MeasurementTimeseriesMetadata.parameter{}.NamedValue.value xml_xml, metadata.MeasurementTimeseriesMetadata.startAnchorPoint xml_buffer, metadata.MeasurementTimeseriesMetadata.startAnchorPoint.frame xml_buffer, metadata.MeasurementTimeseriesMetadata.startAnchorPoint.calendarEraName xml_buffer, metadata.MeasurementTimeseriesMetadata.startAnchorPoint.indeterminatePosition xml_char(7), metadata.MeasurementTimeseriesMetadata.endAnchorPoint xml_buffer, metadata.MeasurementTimeseriesMetadata.endAnchorPoint.frame xml_buffer, metadata.MeasurementTimeseriesMetadata.endAnchorPoint.calendarEraName xml_buffer, metadata.MeasurementTimeseriesMetadata.endAnchorPoint.indeterminatePosition xml_char(7), metadata.MeasurementTimeseriesMetadata.cumulative xml_boolean, metadata.MeasurementTimeseriesMetadata.accumulationAnchorTime xml_buffer, metadata.MeasurementTimeseriesMetadata.accumulationAnchorTime.frame xml_buffer, metadata.MeasurementTimeseriesMetadata.accumulationAnchorTime.calendarEraName xml_buffer,
      metadata.MeasurementTimeseriesMetadata.accumulationAnchorTime.indeterminatePosition xml_char(7), metadata.MeasurementTimeseriesMetadata.accumulationIntervalLength xml_buffer, metadata.MeasurementTimeseriesMetadata.maxGapPeriod xml_buffer, metadata.TimeseriesMetadata.temporalExtent.nilReason xml_buffer, metadata.TimeseriesMetadata.temporalExtent.gml_remoteSchema xml_buffer, metadata.TimeseriesMetadata.temporalExtent.xlink_href xml_buffer, metadata.TimeseriesMetadata.temporalExtent.xlink_title xml_buffer, metadata.TimeseriesMetadata.temporalExtent.owns xml_boolean, metadata.TimeseriesMetadata.temporalExtent.gml_TimePeriod.frame xml_buffer, metadata.TimeseriesMetadata.temporalExtent.gml_TimePeriod.gml_id xml_buffer, metadata.TimeseriesMetadata.temporalExtent.gml_TimePeriod.gml_relatedTime{} xml_xml, metadata.TimeseriesMetadata.temporalExtent.gml_TimePeriod.gml_beginPosition xml_buffer, metadata.TimeseriesMetadata.temporalExtent.gml_TimePeriod.gml_beginPosition.frame xml_buffer, metadata.TimeseriesMetadata.temporalExtent.gml_TimePeriod.gml_beginPosition.calendarEraName xml_buffer, metadata.TimeseriesMetadata.temporalExtent.gml_TimePeriod.gml_beginPosition.indeterminatePosition xml_char(7), metadata.TimeseriesMetadata.temporalExtent.gml_TimePeriod.gml_begin.nilReason xml_buffer, metadata.TimeseriesMetadata.temporalExtent.gml_TimePeriod.gml_begin.gml_remoteSchema xml_buffer, metadata.TimeseriesMetadata.temporalExtent.gml_TimePeriod.gml_begin.xlink_href xml_buffer, metadata.TimeseriesMetadata.temporalExtent.gml_TimePeriod.gml_begin.xlink_title xml_buffer, metadata.TimeseriesMetadata.temporalExtent.gml_TimePeriod.gml_begin.owns xml_boolean, metadata.TimeseriesMetadata.temporalExtent.gml_TimePeriod.gml_begin.gml_TimeInstant.frame xml_buffer, metadata.TimeseriesMetadata.temporalExtent.gml_TimePeriod.gml_begin.gml_TimeInstant.gml_id xml_buffer, metadata.TimeseriesMetadata.temporalExtent.gml_TimePeriod.gml_begin.gml_TimeInstant.gml_relatedTime{} xml_xml, metadata.TimeseriesMetadata.temporalExtent.gml_TimePeriod.gml_begin.gml_TimeInstant.gml_timePosition xml_buffer, metadata.TimeseriesMetadata.temporalExtent.gml_TimePeriod.gml_begin.gml_TimeInstant.gml_timePosition.frame xml_buffer, metadata.TimeseriesMetadata.temporalExtent.gml_TimePeriod.gml_begin.gml_TimeInstant.gml_timePosition.calendarEraName xml_buffer, metadata.TimeseriesMetadata.temporalExtent.gml_TimePeriod.gml_begin.gml_TimeInstant.gml_timePosition.indeterminatePosition xml_char(7), metadata.TimeseriesMetadata.temporalExtent.gml_TimePeriod.gml_endPosition xml_buffer, metadata.TimeseriesMetadata.temporalExtent.gml_TimePeriod.gml_endPosition.frame xml_buffer, metadata.TimeseriesMetadata.temporalExtent.gml_TimePeriod.gml_endPosition.calendarEraName xml_buffer,
      metadata.TimeseriesMetadata.temporalExtent.gml_TimePeriod.gml_endPosition.indeterminatePosition xml_char(7), metadata.TimeseriesMetadata.temporalExtent.gml_TimePeriod.gml_end.nilReason xml_buffer, metadata.TimeseriesMetadata.temporalExtent.gml_TimePeriod.gml_end.gml_remoteSchema xml_buffer, metadata.TimeseriesMetadata.temporalExtent.gml_TimePeriod.gml_end.xlink_href xml_buffer, metadata.TimeseriesMetadata.temporalExtent.gml_TimePeriod.gml_end.xlink_title xml_buffer, metadata.TimeseriesMetadata.temporalExtent.gml_TimePeriod.gml_end.owns xml_boolean, metadata.TimeseriesMetadata.temporalExtent.gml_TimePeriod.gml_end.gml_TimeInstant.frame xml_buffer, metadata.TimeseriesMetadata.temporalExtent.gml_TimePeriod.gml_end.gml_TimeInstant.gml_id xml_buffer, metadata.TimeseriesMetadata.temporalExtent.gml_TimePeriod.gml_end.gml_TimeInstant.gml_relatedTime{} xml_xml, metadata.TimeseriesMetadata.temporalExtent.gml_TimePeriod.gml_end.gml_TimeInstant.gml_timePosition xml_buffer, metadata.TimeseriesMetadata.temporalExtent.gml_TimePeriod.gml_end.gml_TimeInstant.gml_timePosition.frame xml_buffer, metadata.TimeseriesMetadata.temporalExtent.gml_TimePeriod.gml_end.gml_TimeInstant.gml_timePosition.calendarEraName xml_buffer, metadata.TimeseriesMetadata.temporalExtent.gml_TimePeriod.gml_end.gml_TimeInstant.gml_timePosition.indeterminatePosition xml_char(7), metadata.TimeseriesMetadata.temporalExtent.gml_TimePeriod.gml_duration xml_buffer, metadata.TimeseriesMetadata.temporalExtent.gml_TimePeriod.gml_timeInterval xml_real64, metadata.TimeseriesMetadata.temporalExtent.gml_TimePeriod.gml_timeInterval.unit xml_buffer, metadata.TimeseriesMetadata.temporalExtent.gml_TimePeriod.gml_timeInterval.radix xml_uint64, metadata.TimeseriesMetadata.temporalExtent.gml_TimePeriod.gml_timeInterval.factor xml_int64, metadata.TimeseriesMetadata.baseTime xml_buffer, metadata.TimeseriesMetadata.baseTime.frame xml_buffer, metadata.TimeseriesMetadata.baseTime.calendarEraName xml_buffer, metadata.TimeseriesMetadata.baseTime.indeterminatePosition xml_char(7), metadata.TimeseriesMetadata.spacing xml_buffer, metadata.TimeseriesMetadata.commentBlock{}.owns xml_boolean, metadata.TimeseriesMetadata.commentBlock{}.CommentBlock.applicablePeriod.nilReason xml_buffer, metadata.TimeseriesMetadata.commentBlock{}.CommentBlock.applicablePeriod.gml_remoteSchema xml_buffer, metadata.TimeseriesMetadata.commentBlock{}.CommentBlock.applicablePeriod.xlink_href xml_buffer, metadata.TimeseriesMetadata.commentBlock{}.CommentBlock.applicablePeriod.xlink_title xml_buffer, metadata.TimeseriesMetadata.commentBlock{}.CommentBlock.applicablePeriod.owns xml_boolean, metadata.TimeseriesMetadata.commentBlock{}.CommentBlock.applicablePeriod.gml_TimePeriod.frame xml_buffer,
      metadata.TimeseriesMetadata.commentBlock{}.CommentBlock.applicablePeriod.gml_TimePeriod.gml_id xml_buffer, metadata.TimeseriesMetadata.commentBlock{}.CommentBlock.applicablePeriod.gml_TimePeriod.gml_relatedTime{} xml_xml, metadata.TimeseriesMetadata.commentBlock{}.CommentBlock.applicablePeriod.gml_TimePeriod.gml_beginPosition xml_buffer, metadata.TimeseriesMetadata.commentBlock{}.CommentBlock.applicablePeriod.gml_TimePeriod.gml_beginPosition.frame xml_buffer, metadata.TimeseriesMetadata.commentBlock{}.CommentBlock.applicablePeriod.gml_TimePeriod.gml_beginPosition.calendarEraName xml_buffer, metadata.TimeseriesMetadata.commentBlock{}.CommentBlock.applicablePeriod.gml_TimePeriod.gml_beginPosition.indeterminatePosition xml_char(7), metadata.TimeseriesMetadata.commentBlock{}.CommentBlock.applicablePeriod.gml_TimePeriod.gml_begin.nilReason xml_buffer, metadata.TimeseriesMetadata.commentBlock{}.CommentBlock.applicablePeriod.gml_TimePeriod.gml_begin.gml_remoteSchema xml_buffer, metadata.TimeseriesMetadata.commentBlock{}.CommentBlock.applicablePeriod.gml_TimePeriod.gml_begin.xlink_href xml_buffer, metadata.TimeseriesMetadata.commentBlock{}.CommentBlock.applicablePeriod.gml_TimePeriod.gml_begin.xlink_title xml_buffer, metadata.TimeseriesMetadata.commentBlock{}.CommentBlock.applicablePeriod.gml_TimePeriod.gml_begin.owns xml_boolean, metadata.TimeseriesMetadata.commentBlock{}.CommentBlock.applicablePeriod.gml_TimePeriod.gml_begin.gml_TimeInstant.frame xml_buffer, metadata.TimeseriesMetadata.commentBlock{}.CommentBlock.applicablePeriod.gml_TimePeriod.gml_begin.gml_TimeInstant.gml_id xml_buffer, metadata.TimeseriesMetadata.commentBlock{}.CommentBlock.applicablePeriod.gml_TimePeriod.gml_begin.gml_TimeInstant.gml_relatedTime{} xml_xml, metadata.TimeseriesMetadata.commentBlock{}.CommentBlock.applicablePeriod.gml_TimePeriod.gml_begin.gml_TimeInstant.gml_timePosition xml_buffer, metadata.TimeseriesMetadata.commentBlock{}.CommentBlock.applicablePeriod.gml_TimePeriod.gml_begin.gml_TimeInstant.gml_timePosition.frame xml_buffer, metadata.TimeseriesMetadata.commentBlock{}.CommentBlock.applicablePeriod.gml_TimePeriod.gml_begin.gml_TimeInstant.gml_timePosition.calendarEraName xml_buffer, metadata.TimeseriesMetadata.commentBlock{}.CommentBlock.applicablePeriod.gml_TimePeriod.gml_begin.gml_TimeInstant.gml_timePosition.indeterminatePosition xml_char(7), metadata.TimeseriesMetadata.commentBlock{}.CommentBlock.applicablePeriod.gml_TimePeriod.gml_endPosition xml_buffer, metadata.TimeseriesMetadata.commentBlock{}.CommentBlock.applicablePeriod.gml_TimePeriod.gml_endPosition.frame xml_buffer, metadata.TimeseriesMetadata.commentBlock{}.CommentBlock.applicablePeriod.gml_TimePeriod.gml_endPosition.calendarEraName xml_buffer, metadata.TimeseriesMetadata.commentBlock{}.CommentBlock.applicablePeriod.gml_TimePeriod.gml_endPosition.indeterminatePosition xml_char(7), metadata.TimeseriesMetadata.commentBlock{}.CommentBlock.applicablePeriod.gml_TimePeriod.gml_end.nilReason xml_buffer, metadata.TimeseriesMetadata.commentBlock{}.CommentBlock.applicablePeriod.gml_TimePeriod.gml_end.gml_remoteSchema xml_buffer, metadata.TimeseriesMetadata.commentBlock{}.CommentBlock.applicablePeriod.gml_TimePeriod.gml_end.xlink_href xml_buffer, metadata.TimeseriesMetadata.commentBlock{}.CommentBlock.applicablePeriod.gml_TimePeriod.gml_end.xlink_title xml_buffer, metadata.TimeseriesMetadata.commentBlock{}.CommentBlock.applicablePeriod.gml_TimePeriod.gml_end.owns xml_boolean, metadata.TimeseriesMetadata.commentBlock{}.CommentBlock.applicablePeriod.gml_TimePeriod.gml_end.gml_TimeInstant.frame xml_buffer, metadata.TimeseriesMetadata.commentBlock{}.CommentBlock.applicablePeriod.gml_TimePeriod.gml_end.gml_TimeInstant.gml_id xml_buffer, metadata.TimeseriesMetadata.commentBlock{}.CommentBlock.applicablePeriod.gml_TimePeriod.gml_end.gml_TimeInstant.gml_relatedTime{} xml_xml,
      metadata.TimeseriesMetadata.commentBlock{}.CommentBlock.applicablePeriod.gml_TimePeriod.gml_end.gml_TimeInstant.gml_timePosition xml_buffer, metadata.TimeseriesMetadata.commentBlock{}.CommentBlock.applicablePeriod.gml_TimePeriod.gml_end.gml_TimeInstant.gml_timePosition.frame xml_buffer, metadata.TimeseriesMetadata.commentBlock{}.CommentBlock.applicablePeriod.gml_TimePeriod.gml_end.gml_TimeInstant.gml_timePosition.calendarEraName xml_buffer, metadata.TimeseriesMetadata.commentBlock{}.CommentBlock.applicablePeriod.gml_TimePeriod.gml_end.gml_TimeInstant.gml_timePosition.indeterminatePosition xml_char(7), metadata.TimeseriesMetadata.commentBlock{}.CommentBlock.applicablePeriod.gml_TimePeriod.gml_duration xml_buffer, metadata.TimeseriesMetadata.commentBlock{}.CommentBlock.applicablePeriod.gml_TimePeriod.gml_timeInterval xml_real64, metadata.TimeseriesMetadata.commentBlock{}.CommentBlock.applicablePeriod.gml_TimePeriod.gml_timeInterval.unit xml_buffer, metadata.TimeseriesMetadata.commentBlock{}.CommentBlock.applicablePeriod.gml_TimePeriod.gml_timeInterval.radix xml_uint64, metadata.TimeseriesMetadata.commentBlock{}.CommentBlock.applicablePeriod.gml_TimePeriod.gml_timeInterval.factor xml_int64, metadata.TimeseriesMetadata.commentBlock{}.CommentBlock.comment xml_buffer, metadata.TimeseriesMetadata.parameter{}.nilReason xml_buffer, metadata.TimeseriesMetadata.parameter{}.gml_remoteSchema xml_buffer, metadata.TimeseriesMetadata.parameter{}.xlink_href xml_buffer, metadata.TimeseriesMetadata.parameter{}.xlink_title xml_buffer, metadata.TimeseriesMetadata.parameter{}.NamedValue.name.owns xml_boolean, metadata.TimeseriesMetadata.parameter{}.NamedValue.name.nilReason xml_buffer, metadata.TimeseriesMetadata.parameter{}.NamedValue.name.gml_remoteSchema xml_buffer, metadata.TimeseriesMetadata.parameter{}.NamedValue.name.xlink_href xml_buffer, metadata.TimeseriesMetadata.parameter{}.NamedValue.name.xlink_title xml_buffer, metadata.TimeseriesMetadata.parameter{}.NamedValue.value xml_xml, defaultPointMetadata{} xml_xml, defaultPointMetadata{}.owns xml_boolean, point{}.MeasurementTVP.time xml_buffer, point{}.MeasurementTVP.time.frame xml_buffer, point{}.MeasurementTVP.time.calendarEraName xml_buffer, point{}.MeasurementTVP.time.indeterminatePosition xml_char(7), point{}.MeasurementTVP.value xml_real64, point{}.MeasurementTVP.value.uom xml_buffer, point{}.MeasurementTVP.value.xsi_nil xml_boolean, point{}.MeasurementTVP.metadata.owns xml_boolean,
      point{}.MeasurementTVP.metadata.TVPMeasurementMetadata.quality.owns xml_boolean, point{}.MeasurementTVP.metadata.TVPMeasurementMetadata.quality.nilReason xml_buffer, point{}.MeasurementTVP.metadata.TVPMeasurementMetadata.quality.gml_remoteSchema xml_buffer, point{}.MeasurementTVP.metadata.TVPMeasurementMetadata.quality.xlink_href xml_buffer, point{}.MeasurementTVP.metadata.TVPMeasurementMetadata.quality.xlink_title xml_buffer, point{}.MeasurementTVP.metadata.TVPMeasurementMetadata.nilReason.owns xml_boolean, point{}.MeasurementTVP.metadata.TVPMeasurementMetadata.nilReason.nilReason xml_buffer, point{}.MeasurementTVP.metadata.TVPMeasurementMetadata.nilReason.gml_remoteSchema xml_buffer, point{}.MeasurementTVP.metadata.TVPMeasurementMetadata.nilReason.xlink_href xml_buffer, point{}.MeasurementTVP.metadata.TVPMeasurementMetadata.nilReason.xlink_title xml_buffer, point{}.MeasurementTVP.metadata.TVPMeasurementMetadata.comment xml_buffer, point{}.MeasurementTVP.metadata.TVPMeasurementMetadata.relatedObservation{}.ObservationContext.role.owns xml_boolean, point{}.MeasurementTVP.metadata.TVPMeasurementMetadata.relatedObservation{}.ObservationContext.role.nilReason xml_buffer, point{}.MeasurementTVP.metadata.TVPMeasurementMetadata.relatedObservation{}.ObservationContext.role.gml_remoteSchema xml_buffer, point{}.MeasurementTVP.metadata.TVPMeasurementMetadata.relatedObservation{}.ObservationContext.role.xlink_href xml_buffer, point{}.MeasurementTVP.metadata.TVPMeasurementMetadata.relatedObservation{}.ObservationContext.role.xlink_title xml_buffer, point{}.MeasurementTVP.metadata.TVPMeasurementMetadata.relatedObservation{}.ObservationContext.relatedObservation.owns xml_boolean, point{}.MeasurementTVP.metadata.TVPMeasurementMetadata.relatedObservation{}.ObservationContext.relatedObservation.nilReason xml_buffer, point{}.MeasurementTVP.metadata.TVPMeasurementMetadata.relatedObservation{}.ObservationContext.relatedObservation.gml_remoteSchema xml_buffer, point{}.MeasurementTVP.metadata.TVPMeasurementMetadata.relatedObservation{}.ObservationContext.relatedObservation.xlink_href xml_buffer, point{}.MeasurementTVP.metadata.TVPMeasurementMetadata.relatedObservation{}.ObservationContext.relatedObservation.xlink_title xml_buffer, point{}.MeasurementTVP.metadata.TVPMeasurementMetadata.qualifier{}.xlink_href xml_buffer, point{}.MeasurementTVP.metadata.TVPMeasurementMetadata.qualifier{}.xlink_title xml_buffer, point{}.MeasurementTVP.metadata.TVPMeasurementMetadata.qualifier{}.Quantity.referenceFrame xml_buffer, point{}.MeasurementTVP.metadata.TVPMeasurementMetadata.qualifier{}.Quantity.axisID xml_buffer, point{}.MeasurementTVP.metadata.TVPMeasurementMetadata.qualifier{}.Quantity.updatable xml_boolean, point{}.MeasurementTVP.metadata.TVPMeasurementMetadata.qualifier{}.Quantity.optional xml_boolean, point{}.MeasurementTVP.metadata.TVPMeasurementMetadata.qualifier{}.Quantity.definition xml_buffer, point{}.MeasurementTVP.metadata.TVPMeasurementMetadata.qualifier{}.Quantity.id xml_buffer, point{}.MeasurementTVP.metadata.TVPMeasurementMetadata.qualifier{}.Quantity.extension{} xml_xml,
      point{}.MeasurementTVP.metadata.TVPMeasurementMetadata.qualifier{}.Quantity.identifier xml_buffer, point{}.MeasurementTVP.metadata.TVPMeasurementMetadata.qualifier{}.Quantity.label xml_buffer, point{}.MeasurementTVP.metadata.TVPMeasurementMetadata.qualifier{}.Quantity.description xml_buffer, point{}.MeasurementTVP.metadata.TVPMeasurementMetadata.qualifier{}.Quantity.quality{}.xlink_href xml_buffer, point{}.MeasurementTVP.metadata.TVPMeasurementMetadata.qualifier{}.Quantity.quality{}.xlink_title xml_buffer, point{}.MeasurementTVP.metadata.TVPMeasurementMetadata.qualifier{}.Quantity.quality{}.Quantity xml_xml, point{}.MeasurementTVP.metadata.TVPMeasurementMetadata.qualifier{}.Quantity.quality{}.Quantity.referenceFrame xml_buffer, point{}.MeasurementTVP.metadata.TVPMeasurementMetadata.qualifier{}.Quantity.quality{}.Quantity.axisID xml_buffer, point{}.MeasurementTVP.metadata.TVPMeasurementMetadata.qualifier{}.Quantity.quality{}.Quantity.updatable xml_boolean, point{}.MeasurementTVP.metadata.TVPMeasurementMetadata.qualifier{}.Quantity.quality{}.Quantity.optional xml_boolean, point{}.MeasurementTVP.metadata.TVPMeasurementMetadata.qualifier{}.Quantity.quality{}.Quantity.definition xml_buffer, point{}.MeasurementTVP.metadata.TVPMeasurementMetadata.qualifier{}.Quantity.quality{}.Quantity.id xml_buffer, point{}.MeasurementTVP.metadata.TVPMeasurementMetadata.qualifier{}.Quantity.quality{}.QuantityRange.referenceFrame xml_buffer, point{}.MeasurementTVP.metadata.TVPMeasurementMetadata.qualifier{}.Quantity.quality{}.QuantityRange.axisID xml_buffer, point{}.MeasurementTVP.metadata.TVPMeasurementMetadata.qualifier{}.Quantity.quality{}.QuantityRange.updatable xml_boolean, point{}.MeasurementTVP.metadata.TVPMeasurementMetadata.qualifier{}.Quantity.quality{}.QuantityRange.optional xml_boolean, point{}.MeasurementTVP.metadata.TVPMeasurementMetadata.qualifier{}.Quantity.quality{}.QuantityRange.definition xml_buffer, point{}.MeasurementTVP.metadata.TVPMeasurementMetadata.qualifier{}.Quantity.quality{}.QuantityRange.id xml_buffer, point{}.MeasurementTVP.metadata.TVPMeasurementMetadata.qualifier{}.Quantity.quality{}.QuantityRange.extension{} xml_xml, point{}.MeasurementTVP.metadata.TVPMeasurementMetadata.qualifier{}.Quantity.quality{}.QuantityRange.identifier xml_buffer, point{}.MeasurementTVP.metadata.TVPMeasurementMetadata.qualifier{}.Quantity.quality{}.QuantityRange.label xml_buffer, point{}.MeasurementTVP.metadata.TVPMeasurementMetadata.qualifier{}.Quantity.quality{}.QuantityRange.description xml_buffer, point{}.MeasurementTVP.metadata.TVPMeasurementMetadata.qualifier{}.Quantity.quality{}.QuantityRange.quality{} xml_xml, point{}.MeasurementTVP.metadata.TVPMeasurementMetadata.qualifier{}.Quantity.quality{}.QuantityRange.quality{}.xlink_href xml_buffer, point{}.MeasurementTVP.metadata.TVPMeasurementMetadata.qualifier{}.Quantity.quality{}.QuantityRange.quality{}.xlink_title xml_buffer, point{}.MeasurementTVP.metadata.TVPMeasurementMetadata.qualifier{}.Quantity.quality{}.QuantityRange.nilValues.xlink_href xml_buffer, point{}.MeasurementTVP.metadata.TVPMeasurementMetadata.qualifier{}.Quantity.quality{}.QuantityRange.nilValues.xlink_title xml_buffer, point{}.MeasurementTVP.metadata.TVPMeasurementMetadata.qualifier{}.Quantity.quality{}.QuantityRange.nilValues.NilValues.id xml_buffer, point{}.MeasurementTVP.metadata.TVPMeasurementMetadata.qualifier{}.Quantity.quality{}.QuantityRange.nilValues.NilValues.extension{} xml_xml, point{}.MeasurementTVP.metadata.TVPMeasurementMetadata.qualifier{}.Quantity.quality{}.QuantityRange.nilValues.NilValues.nilValue{} xml_buffer,
      point{}.MeasurementTVP.metadata.TVPMeasurementMetadata.qualifier{}.Quantity.quality{}.QuantityRange.nilValues.NilValues.nilValue{}.reason xml_buffer, point{}.MeasurementTVP.metadata.TVPMeasurementMetadata.qualifier{}.Quantity.quality{}.QuantityRange.uom.code xml_buffer, point{}.MeasurementTVP.metadata.TVPMeasurementMetadata.qualifier{}.Quantity.quality{}.QuantityRange.uom.xlink_href xml_buffer, point{}.MeasurementTVP.metadata.TVPMeasurementMetadata.qualifier{}.Quantity.quality{}.QuantityRange.uom.xlink_title xml_buffer, point{}.MeasurementTVP.metadata.TVPMeasurementMetadata.qualifier{}.Quantity.quality{}.QuantityRange.constraint.xlink_href xml_buffer, point{}.MeasurementTVP.metadata.TVPMeasurementMetadata.qualifier{}.Quantity.quality{}.QuantityRange.constraint.xlink_title xml_buffer, point{}.MeasurementTVP.metadata.TVPMeasurementMetadata.qualifier{}.Quantity.quality{}.QuantityRange.constraint.AllowedValues.id xml_buffer, point{}.MeasurementTVP.metadata.TVPMeasurementMetadata.qualifier{}.Quantity.quality{}.QuantityRange.constraint.AllowedValues.extension{} xml_xml, point{}.MeasurementTVP.metadata.TVPMeasurementMetadata.qualifier{}.Quantity.quality{}.QuantityRange.constraint.AllowedValues.value{} xml_real64, point{}.MeasurementTVP.metadata.TVPMeasurementMetadata.qualifier{}.Quantity.quality{}.QuantityRange.constraint.AllowedValues.interval{} xml_buffer, point{}.MeasurementTVP.metadata.TVPMeasurementMetadata.qualifier{}.Quantity.quality{}.QuantityRange.constraint.AllowedValues.significantFigures xml_int64, point{}.MeasurementTVP.metadata.TVPMeasurementMetadata.qualifier{}.Quantity.quality{}.QuantityRange.value xml_buffer, point{}.MeasurementTVP.metadata.TVPMeasurementMetadata.qualifier{}.Quantity.quality{}.Category.referenceFrame xml_buffer, point{}.MeasurementTVP.metadata.TVPMeasurementMetadata.qualifier{}.Quantity.quality{}.Category.axisID xml_buffer, point{}.MeasurementTVP.metadata.TVPMeasurementMetadata.qualifier{}.Quantity.quality{}.Category.updatable xml_boolean, point{}.MeasurementTVP.metadata.TVPMeasurementMetadata.qualifier{}.Quantity.quality{}.Category.optional xml_boolean, point{}.MeasurementTVP.metadata.TVPMeasurementMetadata.qualifier{}.Quantity.quality{}.Category.definition xml_buffer, point{}.MeasurementTVP.metadata.TVPMeasurementMetadata.qualifier{}.Quantity.quality{}.Category.id xml_buffer, point{}.MeasurementTVP.metadata.TVPMeasurementMetadata.qualifier{}.Quantity.quality{}.Category.extension{} xml_xml, point{}.MeasurementTVP.metadata.TVPMeasurementMetadata.qualifier{}.Quantity.quality{}.Category.identifier xml_buffer, point{}.MeasurementTVP.metadata.TVPMeasurementMetadata.qualifier{}.Quantity.quality{}.Category.label xml_buffer, point{}.MeasurementTVP.metadata.TVPMeasurementMetadata.qualifier{}.Quantity.quality{}.Category.description xml_buffer, point{}.MeasurementTVP.metadata.TVPMeasurementMetadata.qualifier{}.Quantity.quality{}.Category.quality{} xml_xml, point{}.MeasurementTVP.metadata.TVPMeasurementMetadata.qualifier{}.Quantity.quality{}.Category.quality{}.xlink_href xml_buffer, point{}.MeasurementTVP.metadata.TVPMeasurementMetadata.qualifier{}.Quantity.quality{}.Category.quality{}.xlink_title xml_buffer, point{}.MeasurementTVP.metadata.TVPMeasurementMetadata.qualifier{}.Quantity.quality{}.Category.nilValues.xlink_href xml_buffer, point{}.MeasurementTVP.metadata.TVPMeasurementMetadata.qualifier{}.Quantity.quality{}.Category.nilValues.xlink_title xml_buffer, point{}.MeasurementTVP.metadata.TVPMeasurementMetadata.qualifier{}.Quantity.quality{}.Category.nilValues.NilValues.id xml_buffer, point{}.MeasurementTVP.metadata.TVPMeasurementMetadata.qualifier{}.Quantity.quality{}.Category.nilValues.NilValues.extension{} xml_xml, point{}.MeasurementTVP.metadata.TVPMeasurementMetadata.qualifier{}.Quantity.quality{}.Category.nilValues.NilValues.nilValue{} xml_buffer,
      point{}.MeasurementTVP.metadata.TVPMeasurementMetadata.qualifier{}.Quantity.quality{}.Category.nilValues.NilValues.nilValue{}.reason xml_buffer, point{}.MeasurementTVP.metadata.TVPMeasurementMetadata.qualifier{}.Quantity.quality{}.Category.codeSpace.xlink_href xml_buffer, point{}.MeasurementTVP.metadata.TVPMeasurementMetadata.qualifier{}.Quantity.quality{}.Category.codeSpace.xlink_title xml_buffer, point{}.MeasurementTVP.metadata.TVPMeasurementMetadata.qualifier{}.Quantity.quality{}.Category.constraint.xlink_href xml_buffer, point{}.MeasurementTVP.metadata.TVPMeasurementMetadata.qualifier{}.Quantity.quality{}.Category.constraint.xlink_title xml_buffer, point{}.MeasurementTVP.metadata.TVPMeasurementMetadata.qualifier{}.Quantity.quality{}.Category.constraint.AllowedTokens.id xml_buffer, point{}.MeasurementTVP.metadata.TVPMeasurementMetadata.qualifier{}.Quantity.quality{}.Category.constraint.AllowedTokens.extension{} xml_xml, point{}.MeasurementTVP.metadata.TVPMeasurementMetadata.qualifier{}.Quantity.quality{}.Category.constraint.AllowedTokens.value{} xml_buffer, point{}.MeasurementTVP.metadata.TVPMeasurementMetadata.qualifier{}.Quantity.quality{}.Category.constraint.AllowedTokens.pattern xml_buffer, point{}.MeasurementTVP.metadata.TVPMeasurementMetadata.qualifier{}.Quantity.quality{}.Category.value xml_buffer, point{}.MeasurementTVP.metadata.TVPMeasurementMetadata.qualifier{}.Quantity.quality{}.Text.referenceFrame xml_buffer, point{}.MeasurementTVP.metadata.TVPMeasurementMetadata.qualifier{}.Quantity.quality{}.Text.axisID xml_buffer, point{}.MeasurementTVP.metadata.TVPMeasurementMetadata.qualifier{}.Quantity.quality{}.Text.updatable xml_boolean, point{}.MeasurementTVP.metadata.TVPMeasurementMetadata.qualifier{}.Quantity.quality{}.Text.optional xml_boolean, point{}.MeasurementTVP.metadata.TVPMeasurementMetadata.qualifier{}.Quantity.quality{}.Text.definition xml_buffer, point{}.MeasurementTVP.metadata.TVPMeasurementMetadata.qualifier{}.Quantity.quality{}.Text.id xml_buffer, point{}.MeasurementTVP.metadata.TVPMeasurementMetadata.qualifier{}.Quantity.quality{}.Text.extension{} xml_xml, point{}.MeasurementTVP.metadata.TVPMeasurementMetadata.qualifier{}.Quantity.quality{}.Text.identifier xml_buffer, point{}.MeasurementTVP.metadata.TVPMeasurementMetadata.qualifier{}.Quantity.quality{}.Text.label xml_buffer, point{}.MeasurementTVP.metadata.TVPMeasurementMetadata.qualifier{}.Quantity.quality{}.Text.description xml_buffer, point{}.MeasurementTVP.metadata.TVPMeasurementMetadata.qualifier{}.Quantity.quality{}.Text.quality{} xml_xml, point{}.MeasurementTVP.metadata.TVPMeasurementMetadata.qualifier{}.Quantity.quality{}.Text.quality{}.xlink_href xml_buffer, point{}.MeasurementTVP.metadata.TVPMeasurementMetadata.qualifier{}.Quantity.quality{}.Text.quality{}.xlink_title xml_buffer, point{}.MeasurementTVP.metadata.TVPMeasurementMetadata.qualifier{}.Quantity.quality{}.Text.nilValues.xlink_href xml_buffer, point{}.MeasurementTVP.metadata.TVPMeasurementMetadata.qualifier{}.Quantity.quality{}.Text.nilValues.xlink_title xml_buffer, point{}.MeasurementTVP.metadata.TVPMeasurementMetadata.qualifier{}.Quantity.quality{}.Text.nilValues.NilValues.id xml_buffer, point{}.MeasurementTVP.metadata.TVPMeasurementMetadata.qualifier{}.Quantity.quality{}.Text.nilValues.NilValues.extension{} xml_xml, point{}.MeasurementTVP.metadata.TVPMeasurementMetadata.qualifier{}.Quantity.quality{}.Text.nilValues.NilValues.nilValue{} xml_buffer, point{}.MeasurementTVP.metadata.TVPMeasurementMetadata.qualifier{}.Quantity.quality{}.Text.nilValues.NilValues.nilValue{}.reason xml_buffer, point{}.MeasurementTVP.metadata.TVPMeasurementMetadata.qualifier{}.Quantity.quality{}.Text.constraint.xlink_href xml_buffer,
      point{}.MeasurementTVP.metadata.TVPMeasurementMetadata.qualifier{}.Quantity.quality{}.Text.constraint.xlink_title xml_buffer, point{}.MeasurementTVP.metadata.TVPMeasurementMetadata.qualifier{}.Quantity.quality{}.Text.constraint.AllowedTokens.id xml_buffer, point{}.MeasurementTVP.metadata.TVPMeasurementMetadata.qualifier{}.Quantity.quality{}.Text.constraint.AllowedTokens.extension{} xml_xml, point{}.MeasurementTVP.metadata.TVPMeasurementMetadata.qualifier{}.Quantity.quality{}.Text.constraint.AllowedTokens.value{} xml_buffer, point{}.MeasurementTVP.metadata.TVPMeasurementMetadata.qualifier{}.Quantity.quality{}.Text.constraint.AllowedTokens.pattern xml_buffer, point{}.MeasurementTVP.metadata.TVPMeasurementMetadata.qualifier{}.Quantity.quality{}.Text.value xml_buffer, point{}.MeasurementTVP.metadata.TVPMeasurementMetadata.qualifier{}.Quantity.nilValues.xlink_href xml_buffer, point{}.MeasurementTVP.metadata.TVPMeasurementMetadata.qualifier{}.Quantity.nilValues.xlink_title xml_buffer, point{}.MeasurementTVP.metadata.TVPMeasurementMetadata.qualifier{}.Quantity.nilValues.NilValues.id xml_buffer, point{}.MeasurementTVP.metadata.TVPMeasurementMetadata.qualifier{}.Quantity.nilValues.NilValues.extension{} xml_xml, point{}.MeasurementTVP.metadata.TVPMeasurementMetadata.qualifier{}.Quantity.nilValues.NilValues.nilValue{} xml_buffer, point{}.MeasurementTVP.metadata.TVPMeasurementMetadata.qualifier{}.Quantity.nilValues.NilValues.nilValue{}.reason xml_buffer, point{}.MeasurementTVP.metadata.TVPMeasurementMetadata.qualifier{}.Quantity.uom.code xml_buffer, point{}.MeasurementTVP.metadata.TVPMeasurementMetadata.qualifier{}.Quantity.uom.xlink_href xml_buffer, point{}.MeasurementTVP.metadata.TVPMeasurementMetadata.qualifier{}.Quantity.uom.xlink_title xml_buffer, point{}.MeasurementTVP.metadata.TVPMeasurementMetadata.qualifier{}.Quantity.constraint.xlink_href xml_buffer, point{}.MeasurementTVP.metadata.TVPMeasurementMetadata.qualifier{}.Quantity.constraint.xlink_title xml_buffer, point{}.MeasurementTVP.metadata.TVPMeasurementMetadata.qualifier{}.Quantity.constraint.AllowedValues.id xml_buffer, point{}.MeasurementTVP.metadata.TVPMeasurementMetadata.qualifier{}.Quantity.constraint.AllowedValues.extension{} xml_xml, point{}.MeasurementTVP.metadata.TVPMeasurementMetadata.qualifier{}.Quantity.constraint.AllowedValues.value{} xml_real64, point{}.MeasurementTVP.metadata.TVPMeasurementMetadata.qualifier{}.Quantity.constraint.AllowedValues.interval{} xml_buffer, point{}.MeasurementTVP.metadata.TVPMeasurementMetadata.qualifier{}.Quantity.constraint.AllowedValues.significantFigures xml_int64, point{}.MeasurementTVP.metadata.TVPMeasurementMetadata.qualifier{}.Quantity.value xml_real64, point{}.MeasurementTVP.metadata.TVPMeasurementMetadata.qualifier{}.QuantityRange.referenceFrame xml_buffer, point{}.MeasurementTVP.metadata.TVPMeasurementMetadata.qualifier{}.QuantityRange.axisID xml_buffer, point{}.MeasurementTVP.metadata.TVPMeasurementMetadata.qualifier{}.QuantityRange.updatable xml_boolean, point{}.MeasurementTVP.metadata.TVPMeasurementMetadata.qualifier{}.QuantityRange.optional xml_boolean, point{}.MeasurementTVP.metadata.TVPMeasurementMetadata.qualifier{}.QuantityRange.definition xml_buffer, point{}.MeasurementTVP.metadata.TVPMeasurementMetadata.qualifier{}.QuantityRange.id xml_buffer, point{}.MeasurementTVP.metadata.TVPMeasurementMetadata.qualifier{}.QuantityRange.extension{} xml_xml,
      point{}.MeasurementTVP.metadata.TVPMeasurementMetadata.qualifier{}.QuantityRange.identifier xml_buffer, point{}.MeasurementTVP.metadata.TVPMeasurementMetadata.qualifier{}.QuantityRange.label xml_buffer, point{}.MeasurementTVP.metadata.TVPMeasurementMetadata.qualifier{}.QuantityRange.description xml_buffer, point{}.MeasurementTVP.metadata.TVPMeasurementMetadata.qualifier{}.QuantityRange.quality{}.xlink_href xml_buffer, point{}.MeasurementTVP.metadata.TVPMeasurementMetadata.qualifier{}.QuantityRange.quality{}.xlink_title xml_buffer, point{}.MeasurementTVP.metadata.TVPMeasurementMetadata.qualifier{}.QuantityRange.quality{}.Quantity.referenceFrame xml_buffer, point{}.MeasurementTVP.metadata.TVPMeasurementMetadata.qualifier{}.QuantityRange.quality{}.Quantity.axisID xml_buffer, point{}.MeasurementTVP.metadata.TVPMeasurementMetadata.qualifier{}.QuantityRange.quality{}.Quantity.updatable xml_boolean, point{}.MeasurementTVP.metadata.TVPMeasurementMetadata.qualifier{}.QuantityRange.quality{}.Quantity.optional xml_boolean, point{}.MeasurementTVP.metadata.TVPMeasurementMetadata.qualifier{}.QuantityRange.quality{}.Quantity.definition xml_buffer, point{}.MeasurementTVP.metadata.TVPMeasurementMetadata.qualifier{}.QuantityRange.quality{}.Quantity.id xml_buffer, point{}.MeasurementTVP.metadata.TVPMeasurementMetadata.qualifier{}.QuantityRange.quality{}.Quantity.extension{} xml_xml, point{}.MeasurementTVP.metadata.TVPMeasurementMetadata.qualifier{}.QuantityRange.quality{}.Quantity.identifier xml_buffer, point{}.MeasurementTVP.metadata.TVPMeasurementMetadata.qualifier{}.QuantityRange.quality{}.Quantity.label xml_buffer, point{}.MeasurementTVP.metadata.TVPMeasurementMetadata.qualifier{}.QuantityRange.quality{}.Quantity.description xml_buffer, point{}.MeasurementTVP.metadata.TVPMeasurementMetadata.qualifier{}.QuantityRange.quality{}.Quantity.quality{} xml_xml, point{}.MeasurementTVP.metadata.TVPMeasurementMetadata.qualifier{}.QuantityRange.quality{}.Quantity.quality{}.xlink_href xml_buffer, point{}.MeasurementTVP.metadata.TVPMeasurementMetadata.qualifier{}.QuantityRange.quality{}.Quantity.quality{}.xlink_title xml_buffer, point{}.MeasurementTVP.metadata.TVPMeasurementMetadata.qualifier{}.QuantityRange.quality{}.Quantity.nilValues.xlink_href xml_buffer, point{}.MeasurementTVP.metadata.TVPMeasurementMetadata.qualifier{}.QuantityRange.quality{}.Quantity.nilValues.xlink_title xml_buffer, point{}.MeasurementTVP.metadata.TVPMeasurementMetadata.qualifier{}.QuantityRange.quality{}.Quantity.nilValues.NilValues.id xml_buffer, point{}.MeasurementTVP.metadata.TVPMeasurementMetadata.qualifier{}.QuantityRange.quality{}.Quantity.nilValues.NilValues.extension{} xml_xml, point{}.MeasurementTVP.metadata.TVPMeasurementMetadata.qualifier{}.QuantityRange.quality{}.Quantity.nilValues.NilValues.nilValue{} xml_buffer, point{}.MeasurementTVP.metadata.TVPMeasurementMetadata.qualifier{}.QuantityRange.quality{}.Quantity.nilValues.NilValues.nilValue{}.reason xml_buffer, point{}.MeasurementTVP.metadata.TVPMeasurementMetadata.qualifier{}.QuantityRange.quality{}.Quantity.uom.code xml_buffer, point{}.MeasurementTVP.metadata.TVPMeasurementMetadata.qualifier{}.QuantityRange.quality{}.Quantity.uom.xlink_href xml_buffer, point{}.MeasurementTVP.metadata.TVPMeasurementMetadata.qualifier{}.QuantityRange.quality{}.Quantity.uom.xlink_title xml_buffer, point{}.MeasurementTVP.metadata.TVPMeasurementMetadata.qualifier{}.QuantityRange.quality{}.Quantity.constraint.xlink_href xml_buffer, point{}.MeasurementTVP.metadata.TVPMeasurementMetadata.qualifier{}.QuantityRange.quality{}.Quantity.constraint.xlink_title xml_buffer, point{}.MeasurementTVP.metadata.TVPMeasurementMetadata.qualifier{}.QuantityRange.quality{}.Quantity.constraint.AllowedValues.id xml_buffer,
      point{}.MeasurementTVP.metadata.TVPMeasurementMetadata.qualifier{}.QuantityRange.quality{}.Quantity.constraint.AllowedValues.extension{} xml_xml, point{}.MeasurementTVP.metadata.TVPMeasurementMetadata.qualifier{}.QuantityRange.quality{}.Quantity.constraint.AllowedValues.value{} xml_real64, point{}.MeasurementTVP.metadata.TVPMeasurementMetadata.qualifier{}.QuantityRange.quality{}.Quantity.constraint.AllowedValues.interval{} xml_buffer, point{}.MeasurementTVP.metadata.TVPMeasurementMetadata.qualifier{}.QuantityRange.quality{}.Quantity.constraint.AllowedValues.significantFigures xml_int64, point{}.MeasurementTVP.metadata.TVPMeasurementMetadata.qualifier{}.QuantityRange.quality{}.Quantity.value xml_real64, point{}.MeasurementTVP.metadata.TVPMeasurementMetadata.qualifier{}.QuantityRange.quality{}.QuantityRange xml_xml, point{}.MeasurementTVP.metadata.TVPMeasurementMetadata.qualifier{}.QuantityRange.quality{}.QuantityRange.referenceFrame xml_buffer, point{}.MeasurementTVP.metadata.TVPMeasurementMetadata.qualifier{}.QuantityRange.quality{}.QuantityRange.axisID xml_buffer, point{}.MeasurementTVP.metadata.TVPMeasurementMetadata.qualifier{}.QuantityRange.quality{}.QuantityRange.updatable xml_boolean, point{}.MeasurementTVP.metadata.TVPMeasurementMetadata.qualifier{}.QuantityRange.quality{}.QuantityRange.optional xml_boolean, point{}.MeasurementTVP.metadata.TVPMeasurementMetadata.qualifier{}.QuantityRange.quality{}.QuantityRange.definition xml_buffer, point{}.MeasurementTVP.metadata.TVPMeasurementMetadata.qualifier{}.QuantityRange.quality{}.QuantityRange.id xml_buffer, point{}.MeasurementTVP.metadata.TVPMeasurementMetadata.qualifier{}.QuantityRange.quality{}.Category.referenceFrame xml_buffer, point{}.MeasurementTVP.metadata.TVPMeasurementMetadata.qualifier{}.QuantityRange.quality{}.Category.axisID xml_buffer, point{}.MeasurementTVP.metadata.TVPMeasurementMetadata.qualifier{}.QuantityRange.quality{}.Category.updatable xml_boolean, point{}.MeasurementTVP.metadata.TVPMeasurementMetadata.qualifier{}.QuantityRange.quality{}.Category.optional xml_boolean, point{}.MeasurementTVP.metadata.TVPMeasurementMetadata.qualifier{}.QuantityRange.quality{}.Category.definition xml_buffer, point{}.MeasurementTVP.metadata.TVPMeasurementMetadata.qualifier{}.QuantityRange.quality{}.Category.id xml_buffer, point{}.MeasurementTVP.metadata.TVPMeasurementMetadata.qualifier{}.QuantityRange.quality{}.Category.extension{} xml_xml, point{}.MeasurementTVP.metadata.TVPMeasurementMetadata.qualifier{}.QuantityRange.quality{}.Category.identifier xml_buffer, point{}.MeasurementTVP.metadata.TVPMeasurementMetadata.qualifier{}.QuantityRange.quality{}.Category.label xml_buffer, point{}.MeasurementTVP.metadata.TVPMeasurementMetadata.qualifier{}.QuantityRange.quality{}.Category.description xml_buffer, point{}.MeasurementTVP.metadata.TVPMeasurementMetadata.qualifier{}.QuantityRange.quality{}.Category.quality{} xml_xml, point{}.MeasurementTVP.metadata.TVPMeasurementMetadata.qualifier{}.QuantityRange.quality{}.Category.quality{}.xlink_href xml_buffer, point{}.MeasurementTVP.metadata.TVPMeasurementMetadata.qualifier{}.QuantityRange.quality{}.Category.quality{}.xlink_title xml_buffer, point{}.MeasurementTVP.metadata.TVPMeasurementMetadata.qualifier{}.QuantityRange.quality{}.Category.nilValues.xlink_href xml_buffer, point{}.MeasurementTVP.metadata.TVPMeasurementMetadata.qualifier{}.QuantityRange.quality{}.Category.nilValues.xlink_title xml_buffer, point{}.MeasurementTVP.metadata.TVPMeasurementMetadata.qualifier{}.QuantityRange.quality{}.Category.nilValues.NilValues.id xml_buffer, point{}.MeasurementTVP.metadata.TVPMeasurementMetadata.qualifier{}.QuantityRange.quality{}.Category.nilValues.NilValues.extension{} xml_xml, point{}.MeasurementTVP.metadata.TVPMeasurementMetadata.qualifier{}.QuantityRange.quality{}.Category.nilValues.NilValues.nilValue{} xml_buffer,
      point{}.MeasurementTVP.metadata.TVPMeasurementMetadata.qualifier{}.QuantityRange.quality{}.Category.nilValues.NilValues.nilValue{}.reason xml_buffer, point{}.MeasurementTVP.metadata.TVPMeasurementMetadata.qualifier{}.QuantityRange.quality{}.Category.codeSpace.xlink_href xml_buffer, point{}.MeasurementTVP.metadata.TVPMeasurementMetadata.qualifier{}.QuantityRange.quality{}.Category.codeSpace.xlink_title xml_buffer, point{}.MeasurementTVP.metadata.TVPMeasurementMetadata.qualifier{}.QuantityRange.quality{}.Category.constraint.xlink_href xml_buffer, point{}.MeasurementTVP.metadata.TVPMeasurementMetadata.qualifier{}.QuantityRange.quality{}.Category.constraint.xlink_title xml_buffer, point{}.MeasurementTVP.metadata.TVPMeasurementMetadata.qualifier{}.QuantityRange.quality{}.Category.constraint.AllowedTokens.id xml_buffer, point{}.MeasurementTVP.metadata.TVPMeasurementMetadata.qualifier{}.QuantityRange.quality{}.Category.constraint.AllowedTokens.extension{} xml_xml, point{}.MeasurementTVP.metadata.TVPMeasurementMetadata.qualifier{}.QuantityRange.quality{}.Category.constraint.AllowedTokens.value{} xml_buffer, point{}.MeasurementTVP.metadata.TVPMeasurementMetadata.qualifier{}.QuantityRange.quality{}.Category.constraint.AllowedTokens.pattern xml_buffer, point{}.MeasurementTVP.metadata.TVPMeasurementMetadata.qualifier{}.QuantityRange.quality{}.Category.value xml_buffer, point{}.MeasurementTVP.metadata.TVPMeasurementMetadata.qualifier{}.QuantityRange.quality{}.Text.referenceFrame xml_buffer, point{}.MeasurementTVP.metadata.TVPMeasurementMetadata.qualifier{}.QuantityRange.quality{}.Text.axisID xml_buffer, point{}.MeasurementTVP.metadata.TVPMeasurementMetadata.qualifier{}.QuantityRange.quality{}.Text.updatable xml_boolean, point{}.MeasurementTVP.metadata.TVPMeasurementMetadata.qualifier{}.QuantityRange.quality{}.Text.optional xml_boolean, point{}.MeasurementTVP.metadata.TVPMeasurementMetadata.qualifier{}.QuantityRange.quality{}.Text.definition xml_buffer, point{}.MeasurementTVP.metadata.TVPMeasurementMetadata.qualifier{}.QuantityRange.quality{}.Text.id xml_buffer, point{}.MeasurementTVP.metadata.TVPMeasurementMetadata.qualifier{}.QuantityRange.quality{}.Text.extension{} xml_xml, point{}.MeasurementTVP.metadata.TVPMeasurementMetadata.qualifier{}.QuantityRange.quality{}.Text.identifier xml_buffer, point{}.MeasurementTVP.metadata.TVPMeasurementMetadata.qualifier{}.QuantityRange.quality{}.Text.label xml_buffer, point{}.MeasurementTVP.metadata.TVPMeasurementMetadata.qualifier{}.QuantityRange.quality{}.Text.description xml_buffer, point{}.MeasurementTVP.metadata.TVPMeasurementMetadata.qualifier{}.QuantityRange.quality{}.Text.quality{} xml_xml, point{}.MeasurementTVP.metadata.TVPMeasurementMetadata.qualifier{}.QuantityRange.quality{}.Text.quality{}.xlink_href xml_buffer, point{}.MeasurementTVP.metadata.TVPMeasurementMetadata.qualifier{}.QuantityRange.quality{}.Text.quality{}.xlink_title xml_buffer, point{}.MeasurementTVP.metadata.TVPMeasurementMetadata.qualifier{}.QuantityRange.quality{}.Text.nilValues.xlink_href xml_buffer, point{}.MeasurementTVP.metadata.TVPMeasurementMetadata.qualifier{}.QuantityRange.quality{}.Text.nilValues.xlink_title xml_buffer, point{}.MeasurementTVP.metadata.TVPMeasurementMetadata.qualifier{}.QuantityRange.quality{}.Text.nilValues.NilValues.id xml_buffer, point{}.MeasurementTVP.metadata.TVPMeasurementMetadata.qualifier{}.QuantityRange.quality{}.Text.nilValues.NilValues.extension{} xml_xml, point{}.MeasurementTVP.metadata.TVPMeasurementMetadata.qualifier{}.QuantityRange.quality{}.Text.nilValues.NilValues.nilValue{} xml_buffer, point{}.MeasurementTVP.metadata.TVPMeasurementMetadata.qualifier{}.QuantityRange.quality{}.Text.nilValues.NilValues.nilValue{}.reason xml_buffer, point{}.MeasurementTVP.metadata.TVPMeasurementMetadata.qualifier{}.QuantityRange.quality{}.Text.constraint.xlink_href xml_buffer,
      point{}.MeasurementTVP.metadata.TVPMeasurementMetadata.qualifier{}.QuantityRange.quality{}.Text.constraint.xlink_title xml_buffer, point{}.MeasurementTVP.metadata.TVPMeasurementMetadata.qualifier{}.QuantityRange.quality{}.Text.constraint.AllowedTokens.id xml_buffer, point{}.MeasurementTVP.metadata.TVPMeasurementMetadata.qualifier{}.QuantityRange.quality{}.Text.constraint.AllowedTokens.extension{} xml_xml, point{}.MeasurementTVP.metadata.TVPMeasurementMetadata.qualifier{}.QuantityRange.quality{}.Text.constraint.AllowedTokens.value{} xml_buffer, point{}.MeasurementTVP.metadata.TVPMeasurementMetadata.qualifier{}.QuantityRange.quality{}.Text.constraint.AllowedTokens.pattern xml_buffer, point{}.MeasurementTVP.metadata.TVPMeasurementMetadata.qualifier{}.QuantityRange.quality{}.Text.value xml_buffer, point{}.MeasurementTVP.metadata.TVPMeasurementMetadata.qualifier{}.QuantityRange.nilValues.xlink_href xml_buffer, point{}.MeasurementTVP.metadata.TVPMeasurementMetadata.qualifier{}.QuantityRange.nilValues.xlink_title xml_buffer, point{}.MeasurementTVP.metadata.TVPMeasurementMetadata.qualifier{}.QuantityRange.nilValues.NilValues.id xml_buffer, point{}.MeasurementTVP.metadata.TVPMeasurementMetadata.qualifier{}.QuantityRange.nilValues.NilValues.extension{} xml_xml, point{}.MeasurementTVP.metadata.TVPMeasurementMetadata.qualifier{}.QuantityRange.nilValues.NilValues.nilValue{} xml_buffer, point{}.MeasurementTVP.metadata.TVPMeasurementMetadata.qualifier{}.QuantityRange.nilValues.NilValues.nilValue{}.reason xml_buffer, point{}.MeasurementTVP.metadata.TVPMeasurementMetadata.qualifier{}.QuantityRange.uom.code xml_buffer, point{}.MeasurementTVP.metadata.TVPMeasurementMetadata.qualifier{}.QuantityRange.uom.xlink_href xml_buffer, point{}.MeasurementTVP.metadata.TVPMeasurementMetadata.qualifier{}.QuantityRange.uom.xlink_title xml_buffer, point{}.MeasurementTVP.metadata.TVPMeasurementMetadata.qualifier{}.QuantityRange.constraint.xlink_href xml_buffer, point{}.MeasurementTVP.metadata.TVPMeasurementMetadata.qualifier{}.QuantityRange.constraint.xlink_title xml_buffer, point{}.MeasurementTVP.metadata.TVPMeasurementMetadata.qualifier{}.QuantityRange.constraint.AllowedValues.id xml_buffer, point{}.MeasurementTVP.metadata.TVPMeasurementMetadata.qualifier{}.QuantityRange.constraint.AllowedValues.extension{} xml_xml, point{}.MeasurementTVP.metadata.TVPMeasurementMetadata.qualifier{}.QuantityRange.constraint.AllowedValues.value{} xml_real64, point{}.MeasurementTVP.metadata.TVPMeasurementMetadata.qualifier{}.QuantityRange.constraint.AllowedValues.interval{} xml_buffer, point{}.MeasurementTVP.metadata.TVPMeasurementMetadata.qualifier{}.QuantityRange.constraint.AllowedValues.significantFigures xml_int64, point{}.MeasurementTVP.metadata.TVPMeasurementMetadata.qualifier{}.QuantityRange.value xml_buffer, point{}.MeasurementTVP.metadata.TVPMeasurementMetadata.qualifier{}.Category.referenceFrame xml_buffer, point{}.MeasurementTVP.metadata.TVPMeasurementMetadata.qualifier{}.Category.axisID xml_buffer, point{}.MeasurementTVP.metadata.TVPMeasurementMetadata.qualifier{}.Category.updatable xml_boolean, point{}.MeasurementTVP.metadata.TVPMeasurementMetadata.qualifier{}.Category.optional xml_boolean, point{}.MeasurementTVP.metadata.TVPMeasurementMetadata.qualifier{}.Category.definition xml_buffer, point{}.MeasurementTVP.metadata.TVPMeasurementMetadata.qualifier{}.Category.id xml_buffer, point{}.MeasurementTVP.metadata.TVPMeasurementMetadata.qualifier{}.Category.extension{} xml_xml,
      point{}.MeasurementTVP.metadata.TVPMeasurementMetadata.qualifier{}.Category.identifier xml_buffer, point{}.MeasurementTVP.metadata.TVPMeasurementMetadata.qualifier{}.Category.label xml_buffer, point{}.MeasurementTVP.metadata.TVPMeasurementMetadata.qualifier{}.Category.description xml_buffer, point{}.MeasurementTVP.metadata.TVPMeasurementMetadata.qualifier{}.Category.quality{}.xlink_href xml_buffer, point{}.MeasurementTVP.metadata.TVPMeasurementMetadata.qualifier{}.Category.quality{}.xlink_title xml_buffer, point{}.MeasurementTVP.metadata.TVPMeasurementMetadata.qualifier{}.Category.quality{}.Quantity.referenceFrame xml_buffer, point{}.MeasurementTVP.metadata.TVPMeasurementMetadata.qualifier{}.Category.quality{}.Quantity.axisID xml_buffer, point{}.MeasurementTVP.metadata.TVPMeasurementMetadata.qualifier{}.Category.quality{}.Quantity.updatable xml_boolean, point{}.MeasurementTVP.metadata.TVPMeasurementMetadata.qualifier{}.Category.quality{}.Quantity.optional xml_boolean, point{}.MeasurementTVP.metadata.TVPMeasurementMetadata.qualifier{}.Category.quality{}.Quantity.definition xml_buffer, point{}.MeasurementTVP.metadata.TVPMeasurementMetadata.qualifier{}.Category.quality{}.Quantity.id xml_buffer, point{}.MeasurementTVP.metadata.TVPMeasurementMetadata.qualifier{}.Category.quality{}.Quantity.extension{} xml_xml, point{}.MeasurementTVP.metadata.TVPMeasurementMetadata.qualifier{}.Category.quality{}.Quantity.identifier xml_buffer, point{}.MeasurementTVP.metadata.TVPMeasurementMetadata.qualifier{}.Category.quality{}.Quantity.label xml_buffer, point{}.MeasurementTVP.metadata.TVPMeasurementMetadata.qualifier{}.Category.quality{}.Quantity.description xml_buffer, point{}.MeasurementTVP.metadata.TVPMeasurementMetadata.qualifier{}.Category.quality{}.Quantity.quality{} xml_xml, point{}.MeasurementTVP.metadata.TVPMeasurementMetadata.qualifier{}.Category.quality{}.Quantity.quality{}.xlink_href xml_buffer, point{}.MeasurementTVP.metadata.TVPMeasurementMetadata.qualifier{}.Category.quality{}.Quantity.quality{}.xlink_title xml_buffer, point{}.MeasurementTVP.metadata.TVPMeasurementMetadata.qualifier{}.Category.quality{}.Quantity.nilValues.xlink_href xml_buffer, point{}.MeasurementTVP.metadata.TVPMeasurementMetadata.qualifier{}.Category.quality{}.Quantity.nilValues.xlink_title xml_buffer, point{}.MeasurementTVP.metadata.TVPMeasurementMetadata.qualifier{}.Category.quality{}.Quantity.nilValues.NilValues.id xml_buffer, point{}.MeasurementTVP.metadata.TVPMeasurementMetadata.qualifier{}.Category.quality{}.Quantity.nilValues.NilValues.extension{} xml_xml, point{}.MeasurementTVP.metadata.TVPMeasurementMetadata.qualifier{}.Category.quality{}.Quantity.nilValues.NilValues.nilValue{} xml_buffer, point{}.MeasurementTVP.metadata.TVPMeasurementMetadata.qualifier{}.Category.quality{}.Quantity.nilValues.NilValues.nilValue{}.reason xml_buffer, point{}.MeasurementTVP.metadata.TVPMeasurementMetadata.qualifier{}.Category.quality{}.Quantity.uom.code xml_buffer, point{}.MeasurementTVP.metadata.TVPMeasurementMetadata.qualifier{}.Category.quality{}.Quantity.uom.xlink_href xml_buffer, point{}.MeasurementTVP.metadata.TVPMeasurementMetadata.qualifier{}.Category.quality{}.Quantity.uom.xlink_title xml_buffer, point{}.MeasurementTVP.metadata.TVPMeasurementMetadata.qualifier{}.Category.quality{}.Quantity.constraint.xlink_href xml_buffer, point{}.MeasurementTVP.metadata.TVPMeasurementMetadata.qualifier{}.Category.quality{}.Quantity.constraint.xlink_title xml_buffer, point{}.MeasurementTVP.metadata.TVPMeasurementMetadata.qualifier{}.Category.quality{}.Quantity.constraint.AllowedValues.id xml_buffer,
      point{}.MeasurementTVP.metadata.TVPMeasurementMetadata.qualifier{}.Category.quality{}.Quantity.constraint.AllowedValues.extension{} xml_xml, point{}.MeasurementTVP.metadata.TVPMeasurementMetadata.qualifier{}.Category.quality{}.Quantity.constraint.AllowedValues.value{} xml_real64, point{}.MeasurementTVP.metadata.TVPMeasurementMetadata.qualifier{}.Category.quality{}.Quantity.constraint.AllowedValues.interval{} xml_buffer, point{}.MeasurementTVP.metadata.TVPMeasurementMetadata.qualifier{}.Category.quality{}.Quantity.constraint.AllowedValues.significantFigures xml_int64, point{}.MeasurementTVP.metadata.TVPMeasurementMetadata.qualifier{}.Category.quality{}.Quantity.value xml_real64, point{}.MeasurementTVP.metadata.TVPMeasurementMetadata.qualifier{}.Category.quality{}.QuantityRange.referenceFrame xml_buffer, point{}.MeasurementTVP.metadata.TVPMeasurementMetadata.qualifier{}.Category.quality{}.QuantityRange.axisID xml_buffer, point{}.MeasurementTVP.metadata.TVPMeasurementMetadata.qualifier{}.Category.quality{}.QuantityRange.updatable xml_boolean, point{}.MeasurementTVP.metadata.TVPMeasurementMetadata.qualifier{}.Category.quality{}.QuantityRange.optional xml_boolean, point{}.MeasurementTVP.metadata.TVPMeasurementMetadata.qualifier{}.Category.quality{}.QuantityRange.definition xml_buffer, point{}.MeasurementTVP.metadata.TVPMeasurementMetadata.qualifier{}.Category.quality{}.QuantityRange.id xml_buffer, point{}.MeasurementTVP.metadata.TVPMeasurementMetadata.qualifier{}.Category.quality{}.QuantityRange.extension{} xml_xml, point{}.MeasurementTVP.metadata.TVPMeasurementMetadata.qualifier{}.Category.quality{}.QuantityRange.identifier xml_buffer, point{}.MeasurementTVP.metadata.TVPMeasurementMetadata.qualifier{}.Category.quality{}.QuantityRange.label xml_buffer, point{}.MeasurementTVP.metadata.TVPMeasurementMetadata.qualifier{}.Category.quality{}.QuantityRange.description xml_buffer, point{}.MeasurementTVP.metadata.TVPMeasurementMetadata.qualifier{}.Category.quality{}.QuantityRange.quality{} xml_xml, point{}.MeasurementTVP.metadata.TVPMeasurementMetadata.qualifier{}.Category.quality{}.QuantityRange.quality{}.xlink_href xml_buffer, point{}.MeasurementTVP.metadata.TVPMeasurementMetadata.qualifier{}.Category.quality{}.QuantityRange.quality{}.xlink_title xml_buffer, point{}.MeasurementTVP.metadata.TVPMeasurementMetadata.qualifier{}.Category.quality{}.QuantityRange.nilValues.xlink_href xml_buffer, point{}.MeasurementTVP.metadata.TVPMeasurementMetadata.qualifier{}.Category.quality{}.QuantityRange.nilValues.xlink_title xml_buffer, point{}.MeasurementTVP.metadata.TVPMeasurementMetadata.qualifier{}.Category.quality{}.QuantityRange.nilValues.NilValues.id xml_buffer, point{}.MeasurementTVP.metadata.TVPMeasurementMetadata.qualifier{}.Category.quality{}.QuantityRange.nilValues.NilValues.extension{} xml_xml, point{}.MeasurementTVP.metadata.TVPMeasurementMetadata.qualifier{}.Category.quality{}.QuantityRange.nilValues.NilValues.nilValue{} xml_buffer, point{}.MeasurementTVP.metadata.TVPMeasurementMetadata.qualifier{}.Category.quality{}.QuantityRange.nilValues.NilValues.nilValue{}.reason xml_buffer, point{}.MeasurementTVP.metadata.TVPMeasurementMetadata.qualifier{}.Category.quality{}.QuantityRange.uom.code xml_buffer, point{}.MeasurementTVP.metadata.TVPMeasurementMetadata.qualifier{}.Category.quality{}.QuantityRange.uom.xlink_href xml_buffer, point{}.MeasurementTVP.metadata.TVPMeasurementMetadata.qualifier{}.Category.quality{}.QuantityRange.uom.xlink_title xml_buffer, point{}.MeasurementTVP.metadata.TVPMeasurementMetadata.qualifier{}.Category.quality{}.QuantityRange.constraint.xlink_href xml_buffer, point{}.MeasurementTVP.metadata.TVPMeasurementMetadata.qualifier{}.Category.quality{}.QuantityRange.constraint.xlink_title xml_buffer, point{}.MeasurementTVP.metadata.TVPMeasurementMetadata.qualifier{}.Category.quality{}.QuantityRange.constraint.AllowedValues.id xml_buffer,
      point{}.MeasurementTVP.metadata.TVPMeasurementMetadata.qualifier{}.Category.quality{}.QuantityRange.constraint.AllowedValues.extension{} xml_xml, point{}.MeasurementTVP.metadata.TVPMeasurementMetadata.qualifier{}.Category.quality{}.QuantityRange.constraint.AllowedValues.value{} xml_real64, point{}.MeasurementTVP.metadata.TVPMeasurementMetadata.qualifier{}.Category.quality{}.QuantityRange.constraint.AllowedValues.interval{} xml_buffer, point{}.MeasurementTVP.metadata.TVPMeasurementMetadata.qualifier{}.Category.quality{}.QuantityRange.constraint.AllowedValues.significantFigures xml_int64, point{}.MeasurementTVP.metadata.TVPMeasurementMetadata.qualifier{}.Category.quality{}.QuantityRange.value xml_buffer, point{}.MeasurementTVP.metadata.TVPMeasurementMetadata.qualifier{}.Category.quality{}.Category xml_xml, point{}.MeasurementTVP.metadata.TVPMeasurementMetadata.qualifier{}.Category.quality{}.Category.referenceFrame xml_buffer, point{}.MeasurementTVP.metadata.TVPMeasurementMetadata.qualifier{}.Category.quality{}.Category.axisID xml_buffer, point{}.MeasurementTVP.metadata.TVPMeasurementMetadata.qualifier{}.Category.quality{}.Category.updatable xml_boolean, point{}.MeasurementTVP.metadata.TVPMeasurementMetadata.qualifier{}.Category.quality{}.Category.optional xml_boolean, point{}.MeasurementTVP.metadata.TVPMeasurementMetadata.qualifier{}.Category.quality{}.Category.definition xml_buffer, point{}.MeasurementTVP.metadata.TVPMeasurementMetadata.qualifier{}.Category.quality{}.Category.id xml_buffer, point{}.MeasurementTVP.metadata.TVPMeasurementMetadata.qualifier{}.Category.quality{}.Text.referenceFrame xml_buffer, point{}.MeasurementTVP.metadata.TVPMeasurementMetadata.qualifier{}.Category.quality{}.Text.axisID xml_buffer, point{}.MeasurementTVP.metadata.TVPMeasurementMetadata.qualifier{}.Category.quality{}.Text.updatable xml_boolean, point{}.MeasurementTVP.metadata.TVPMeasurementMetadata.qualifier{}.Category.quality{}.Text.optional xml_boolean, point{}.MeasurementTVP.metadata.TVPMeasurementMetadata.qualifier{}.Category.quality{}.Text.definition xml_buffer, point{}.MeasurementTVP.metadata.TVPMeasurementMetadata.qualifier{}.Category.quality{}.Text.id xml_buffer, point{}.MeasurementTVP.metadata.TVPMeasurementMetadata.qualifier{}.Category.quality{}.Text.extension{} xml_xml, point{}.MeasurementTVP.metadata.TVPMeasurementMetadata.qualifier{}.Category.quality{}.Text.identifier xml_buffer, point{}.MeasurementTVP.metadata.TVPMeasurementMetadata.qualifier{}.Category.quality{}.Text.label xml_buffer, point{}.MeasurementTVP.metadata.TVPMeasurementMetadata.qualifier{}.Category.quality{}.Text.description xml_buffer, point{}.MeasurementTVP.metadata.TVPMeasurementMetadata.qualifier{}.Category.quality{}.Text.quality{} xml_xml, point{}.MeasurementTVP.metadata.TVPMeasurementMetadata.qualifier{}.Category.quality{}.Text.quality{}.xlink_href xml_buffer, point{}.MeasurementTVP.metadata.TVPMeasurementMetadata.qualifier{}.Category.quality{}.Text.quality{}.xlink_title xml_buffer, point{}.MeasurementTVP.metadata.TVPMeasurementMetadata.qualifier{}.Category.quality{}.Text.nilValues.xlink_href xml_buffer, point{}.MeasurementTVP.metadata.TVPMeasurementMetadata.qualifier{}.Category.quality{}.Text.nilValues.xlink_title xml_buffer, point{}.MeasurementTVP.metadata.TVPMeasurementMetadata.qualifier{}.Category.quality{}.Text.nilValues.NilValues.id xml_buffer, point{}.MeasurementTVP.metadata.TVPMeasurementMetadata.qualifier{}.Category.quality{}.Text.nilValues.NilValues.extension{} xml_xml, point{}.MeasurementTVP.metadata.TVPMeasurementMetadata.qualifier{}.Category.quality{}.Text.nilValues.NilValues.nilValue{} xml_buffer,
      point{}.MeasurementTVP.metadata.TVPMeasurementMetadata.qualifier{}.Category.quality{}.Text.nilValues.NilValues.nilValue{}.reason xml_buffer, point{}.MeasurementTVP.metadata.TVPMeasurementMetadata.qualifier{}.Category.quality{}.Text.constraint.xlink_href xml_buffer, point{}.MeasurementTVP.metadata.TVPMeasurementMetadata.qualifier{}.Category.quality{}.Text.constraint.xlink_title xml_buffer, point{}.MeasurementTVP.metadata.TVPMeasurementMetadata.qualifier{}.Category.quality{}.Text.constraint.AllowedTokens.id xml_buffer, point{}.MeasurementTVP.metadata.TVPMeasurementMetadata.qualifier{}.Category.quality{}.Text.constraint.AllowedTokens.extension{} xml_xml, point{}.MeasurementTVP.metadata.TVPMeasurementMetadata.qualifier{}.Category.quality{}.Text.constraint.AllowedTokens.value{} xml_buffer, point{}.MeasurementTVP.metadata.TVPMeasurementMetadata.qualifier{}.Category.quality{}.Text.constraint.AllowedTokens.pattern xml_buffer, point{}.MeasurementTVP.metadata.TVPMeasurementMetadata.qualifier{}.Category.quality{}.Text.value xml_buffer, point{}.MeasurementTVP.metadata.TVPMeasurementMetadata.qualifier{}.Category.nilValues.xlink_href xml_buffer, point{}.MeasurementTVP.metadata.TVPMeasurementMetadata.qualifier{}.Category.nilValues.xlink_title xml_buffer, point{}.MeasurementTVP.metadata.TVPMeasurementMetadata.qualifier{}.Category.nilValues.NilValues.id xml_buffer, point{}.MeasurementTVP.metadata.TVPMeasurementMetadata.qualifier{}.Category.nilValues.NilValues.extension{} xml_xml, point{}.MeasurementTVP.metadata.TVPMeasurementMetadata.qualifier{}.Category.nilValues.NilValues.nilValue{} xml_buffer, point{}.MeasurementTVP.metadata.TVPMeasurementMetadata.qualifier{}.Category.nilValues.NilValues.nilValue{}.reason xml_buffer, point{}.MeasurementTVP.metadata.TVPMeasurementMetadata.qualifier{}.Category.codeSpace.xlink_href xml_buffer, point{}.MeasurementTVP.metadata.TVPMeasurementMetadata.qualifier{}.Category.codeSpace.xlink_title xml_buffer, point{}.MeasurementTVP.metadata.TVPMeasurementMetadata.qualifier{}.Category.constraint.xlink_href xml_buffer, point{}.MeasurementTVP.metadata.TVPMeasurementMetadata.qualifier{}.Category.constraint.xlink_title xml_buffer, point{}.MeasurementTVP.metadata.TVPMeasurementMetadata.qualifier{}.Category.constraint.AllowedTokens.id xml_buffer, point{}.MeasurementTVP.metadata.TVPMeasurementMetadata.qualifier{}.Category.constraint.AllowedTokens.extension{} xml_xml, point{}.MeasurementTVP.metadata.TVPMeasurementMetadata.qualifier{}.Category.constraint.AllowedTokens.value{} xml_buffer, point{}.MeasurementTVP.metadata.TVPMeasurementMetadata.qualifier{}.Category.constraint.AllowedTokens.pattern xml_buffer, point{}.MeasurementTVP.metadata.TVPMeasurementMetadata.qualifier{}.Category.value xml_buffer, point{}.MeasurementTVP.metadata.TVPMeasurementMetadata.qualifier{}.Text.referenceFrame xml_buffer, point{}.MeasurementTVP.metadata.TVPMeasurementMetadata.qualifier{}.Text.axisID xml_buffer, point{}.MeasurementTVP.metadata.TVPMeasurementMetadata.qualifier{}.Text.updatable xml_boolean, point{}.MeasurementTVP.metadata.TVPMeasurementMetadata.qualifier{}.Text.optional xml_boolean, point{}.MeasurementTVP.metadata.TVPMeasurementMetadata.qualifier{}.Text.definition xml_buffer, point{}.MeasurementTVP.metadata.TVPMeasurementMetadata.qualifier{}.Text.id xml_buffer, point{}.MeasurementTVP.metadata.TVPMeasurementMetadata.qualifier{}.Text.extension{} xml_xml,
      point{}.MeasurementTVP.metadata.TVPMeasurementMetadata.qualifier{}.Text.identifier xml_buffer, point{}.MeasurementTVP.metadata.TVPMeasurementMetadata.qualifier{}.Text.label xml_buffer, point{}.MeasurementTVP.metadata.TVPMeasurementMetadata.qualifier{}.Text.description xml_buffer, point{}.MeasurementTVP.metadata.TVPMeasurementMetadata.qualifier{}.Text.quality{}.xlink_href xml_buffer, point{}.MeasurementTVP.metadata.TVPMeasurementMetadata.qualifier{}.Text.quality{}.xlink_title xml_buffer, point{}.MeasurementTVP.metadata.TVPMeasurementMetadata.qualifier{}.Text.quality{}.Quantity.referenceFrame xml_buffer, point{}.MeasurementTVP.metadata.TVPMeasurementMetadata.qualifier{}.Text.quality{}.Quantity.axisID xml_buffer, point{}.MeasurementTVP.metadata.TVPMeasurementMetadata.qualifier{}.Text.quality{}.Quantity.updatable xml_boolean, point{}.MeasurementTVP.metadata.TVPMeasurementMetadata.qualifier{}.Text.quality{}.Quantity.optional xml_boolean, point{}.MeasurementTVP.metadata.TVPMeasurementMetadata.qualifier{}.Text.quality{}.Quantity.definition xml_buffer, point{}.MeasurementTVP.metadata.TVPMeasurementMetadata.qualifier{}.Text.quality{}.Quantity.id xml_buffer, point{}.MeasurementTVP.metadata.TVPMeasurementMetadata.qualifier{}.Text.quality{}.Quantity.extension{} xml_xml, point{}.MeasurementTVP.metadata.TVPMeasurementMetadata.qualifier{}.Text.quality{}.Quantity.identifier xml_buffer, point{}.MeasurementTVP.metadata.TVPMeasurementMetadata.qualifier{}.Text.quality{}.Quantity.label xml_buffer, point{}.MeasurementTVP.metadata.TVPMeasurementMetadata.qualifier{}.Text.quality{}.Quantity.description xml_buffer, point{}.MeasurementTVP.metadata.TVPMeasurementMetadata.qualifier{}.Text.quality{}.Quantity.quality{} xml_xml, point{}.MeasurementTVP.metadata.TVPMeasurementMetadata.qualifier{}.Text.quality{}.Quantity.quality{}.xlink_href xml_buffer, point{}.MeasurementTVP.metadata.TVPMeasurementMetadata.qualifier{}.Text.quality{}.Quantity.quality{}.xlink_title xml_buffer, point{}.MeasurementTVP.metadata.TVPMeasurementMetadata.qualifier{}.Text.quality{}.Quantity.nilValues.xlink_href xml_buffer, point{}.MeasurementTVP.metadata.TVPMeasurementMetadata.qualifier{}.Text.quality{}.Quantity.nilValues.xlink_title xml_buffer, point{}.MeasurementTVP.metadata.TVPMeasurementMetadata.qualifier{}.Text.quality{}.Quantity.nilValues.NilValues.id xml_buffer, point{}.MeasurementTVP.metadata.TVPMeasurementMetadata.qualifier{}.Text.quality{}.Quantity.nilValues.NilValues.extension{} xml_xml, point{}.MeasurementTVP.metadata.TVPMeasurementMetadata.qualifier{}.Text.quality{}.Quantity.nilValues.NilValues.nilValue{} xml_buffer, point{}.MeasurementTVP.metadata.TVPMeasurementMetadata.qualifier{}.Text.quality{}.Quantity.nilValues.NilValues.nilValue{}.reason xml_buffer, point{}.MeasurementTVP.metadata.TVPMeasurementMetadata.qualifier{}.Text.quality{}.Quantity.uom.code xml_buffer, point{}.MeasurementTVP.metadata.TVPMeasurementMetadata.qualifier{}.Text.quality{}.Quantity.uom.xlink_href xml_buffer, point{}.MeasurementTVP.metadata.TVPMeasurementMetadata.qualifier{}.Text.quality{}.Quantity.uom.xlink_title xml_buffer, point{}.MeasurementTVP.metadata.TVPMeasurementMetadata.qualifier{}.Text.quality{}.Quantity.constraint.xlink_href xml_buffer, point{}.MeasurementTVP.metadata.TVPMeasurementMetadata.qualifier{}.Text.quality{}.Quantity.constraint.xlink_title xml_buffer, point{}.MeasurementTVP.metadata.TVPMeasurementMetadata.qualifier{}.Text.quality{}.Quantity.constraint.AllowedValues.id xml_buffer,
      point{}.MeasurementTVP.metadata.TVPMeasurementMetadata.qualifier{}.Text.quality{}.Quantity.constraint.AllowedValues.extension{} xml_xml, point{}.MeasurementTVP.metadata.TVPMeasurementMetadata.qualifier{}.Text.quality{}.Quantity.constraint.AllowedValues.value{} xml_real64, point{}.MeasurementTVP.metadata.TVPMeasurementMetadata.qualifier{}.Text.quality{}.Quantity.constraint.AllowedValues.interval{} xml_buffer, point{}.MeasurementTVP.metadata.TVPMeasurementMetadata.qualifier{}.Text.quality{}.Quantity.constraint.AllowedValues.significantFigures xml_int64, point{}.MeasurementTVP.metadata.TVPMeasurementMetadata.qualifier{}.Text.quality{}.Quantity.value xml_real64, point{}.MeasurementTVP.metadata.TVPMeasurementMetadata.qualifier{}.Text.quality{}.QuantityRange.referenceFrame xml_buffer, point{}.MeasurementTVP.metadata.TVPMeasurementMetadata.qualifier{}.Text.quality{}.QuantityRange.axisID xml_buffer, point{}.MeasurementTVP.metadata.TVPMeasurementMetadata.qualifier{}.Text.quality{}.QuantityRange.updatable xml_boolean, point{}.MeasurementTVP.metadata.TVPMeasurementMetadata.qualifier{}.Text.quality{}.QuantityRange.optional xml_boolean, point{}.MeasurementTVP.metadata.TVPMeasurementMetadata.qualifier{}.Text.quality{}.QuantityRange.definition xml_buffer, point{}.MeasurementTVP.metadata.TVPMeasurementMetadata.qualifier{}.Text.quality{}.QuantityRange.id xml_buffer, point{}.MeasurementTVP.metadata.TVPMeasurementMetadata.qualifier{}.Text.quality{}.QuantityRange.extension{} xml_xml, point{}.MeasurementTVP.metadata.TVPMeasurementMetadata.qualifier{}.Text.quality{}.QuantityRange.identifier xml_buffer, point{}.MeasurementTVP.metadata.TVPMeasurementMetadata.qualifier{}.Text.quality{}.QuantityRange.label xml_buffer, point{}.MeasurementTVP.metadata.TVPMeasurementMetadata.qualifier{}.Text.quality{}.QuantityRange.description xml_buffer, point{}.MeasurementTVP.metadata.TVPMeasurementMetadata.qualifier{}.Text.quality{}.QuantityRange.quality{} xml_xml, point{}.MeasurementTVP.metadata.TVPMeasurementMetadata.qualifier{}.Text.quality{}.QuantityRange.quality{}.xlink_href xml_buffer, point{}.MeasurementTVP.metadata.TVPMeasurementMetadata.qualifier{}.Text.quality{}.QuantityRange.quality{}.xlink_title xml_buffer, point{}.MeasurementTVP.metadata.TVPMeasurementMetadata.qualifier{}.Text.quality{}.QuantityRange.nilValues.xlink_href xml_buffer, point{}.MeasurementTVP.metadata.TVPMeasurementMetadata.qualifier{}.Text.quality{}.QuantityRange.nilValues.xlink_title xml_buffer, point{}.MeasurementTVP.metadata.TVPMeasurementMetadata.qualifier{}.Text.quality{}.QuantityRange.nilValues.NilValues.id xml_buffer, point{}.MeasurementTVP.metadata.TVPMeasurementMetadata.qualifier{}.Text.quality{}.QuantityRange.nilValues.NilValues.extension{} xml_xml, point{}.MeasurementTVP.metadata.TVPMeasurementMetadata.qualifier{}.Text.quality{}.QuantityRange.nilValues.NilValues.nilValue{} xml_buffer, point{}.MeasurementTVP.metadata.TVPMeasurementMetadata.qualifier{}.Text.quality{}.QuantityRange.nilValues.NilValues.nilValue{}.reason xml_buffer, point{}.MeasurementTVP.metadata.TVPMeasurementMetadata.qualifier{}.Text.quality{}.QuantityRange.uom.code xml_buffer, point{}.MeasurementTVP.metadata.TVPMeasurementMetadata.qualifier{}.Text.quality{}.QuantityRange.uom.xlink_href xml_buffer, point{}.MeasurementTVP.metadata.TVPMeasurementMetadata.qualifier{}.Text.quality{}.QuantityRange.uom.xlink_title xml_buffer, point{}.MeasurementTVP.metadata.TVPMeasurementMetadata.qualifier{}.Text.quality{}.QuantityRange.constraint.xlink_href xml_buffer, point{}.MeasurementTVP.metadata.TVPMeasurementMetadata.qualifier{}.Text.quality{}.QuantityRange.constraint.xlink_title xml_buffer, point{}.MeasurementTVP.metadata.TVPMeasurementMetadata.qualifier{}.Text.quality{}.QuantityRange.constraint.AllowedValues.id xml_buffer,
      point{}.MeasurementTVP.metadata.TVPMeasurementMetadata.qualifier{}.Text.quality{}.QuantityRange.constraint.AllowedValues.extension{} xml_xml, point{}.MeasurementTVP.metadata.TVPMeasurementMetadata.qualifier{}.Text.quality{}.QuantityRange.constraint.AllowedValues.value{} xml_real64, point{}.MeasurementTVP.metadata.TVPMeasurementMetadata.qualifier{}.Text.quality{}.QuantityRange.constraint.AllowedValues.interval{} xml_buffer, point{}.MeasurementTVP.metadata.TVPMeasurementMetadata.qualifier{}.Text.quality{}.QuantityRange.constraint.AllowedValues.significantFigures xml_int64, point{}.MeasurementTVP.metadata.TVPMeasurementMetadata.qualifier{}.Text.quality{}.QuantityRange.value xml_buffer, point{}.MeasurementTVP.metadata.TVPMeasurementMetadata.qualifier{}.Text.quality{}.Category.referenceFrame xml_buffer, point{}.MeasurementTVP.metadata.TVPMeasurementMetadata.qualifier{}.Text.quality{}.Category.axisID xml_buffer, point{}.MeasurementTVP.metadata.TVPMeasurementMetadata.qualifier{}.Text.quality{}.Category.updatable xml_boolean, point{}.MeasurementTVP.metadata.TVPMeasurementMetadata.qualifier{}.Text.quality{}.Category.optional xml_boolean, point{}.MeasurementTVP.metadata.TVPMeasurementMetadata.qualifier{}.Text.quality{}.Category.definition xml_buffer, point{}.MeasurementTVP.metadata.TVPMeasurementMetadata.qualifier{}.Text.quality{}.Category.id xml_buffer, point{}.MeasurementTVP.metadata.TVPMeasurementMetadata.qualifier{}.Text.quality{}.Category.extension{} xml_xml, point{}.MeasurementTVP.metadata.TVPMeasurementMetadata.qualifier{}.Text.quality{}.Category.identifier xml_buffer, point{}.MeasurementTVP.metadata.TVPMeasurementMetadata.qualifier{}.Text.quality{}.Category.label xml_buffer, point{}.MeasurementTVP.metadata.TVPMeasurementMetadata.qualifier{}.Text.quality{}.Category.description xml_buffer, point{}.MeasurementTVP.metadata.TVPMeasurementMetadata.qualifier{}.Text.quality{}.Category.quality{} xml_xml, point{}.MeasurementTVP.metadata.TVPMeasurementMetadata.qualifier{}.Text.quality{}.Category.quality{}.xlink_href xml_buffer, point{}.MeasurementTVP.metadata.TVPMeasurementMetadata.qualifier{}.Text.quality{}.Category.quality{}.xlink_title xml_buffer, point{}.MeasurementTVP.metadata.TVPMeasurementMetadata.qualifier{}.Text.quality{}.Category.nilValues.xlink_href xml_buffer, point{}.MeasurementTVP.metadata.TVPMeasurementMetadata.qualifier{}.Text.quality{}.Category.nilValues.xlink_title xml_buffer, point{}.MeasurementTVP.metadata.TVPMeasurementMetadata.qualifier{}.Text.quality{}.Category.nilValues.NilValues.id xml_buffer, point{}.MeasurementTVP.metadata.TVPMeasurementMetadata.qualifier{}.Text.quality{}.Category.nilValues.NilValues.extension{} xml_xml, point{}.MeasurementTVP.metadata.TVPMeasurementMetadata.qualifier{}.Text.quality{}.Category.nilValues.NilValues.nilValue{} xml_buffer, point{}.MeasurementTVP.metadata.TVPMeasurementMetadata.qualifier{}.Text.quality{}.Category.nilValues.NilValues.nilValue{}.reason xml_buffer, point{}.MeasurementTVP.metadata.TVPMeasurementMetadata.qualifier{}.Text.quality{}.Category.codeSpace.xlink_href xml_buffer, point{}.MeasurementTVP.metadata.TVPMeasurementMetadata.qualifier{}.Text.quality{}.Category.codeSpace.xlink_title xml_buffer, point{}.MeasurementTVP.metadata.TVPMeasurementMetadata.qualifier{}.Text.quality{}.Category.constraint.xlink_href xml_buffer, point{}.MeasurementTVP.metadata.TVPMeasurementMetadata.qualifier{}.Text.quality{}.Category.constraint.xlink_title xml_buffer, point{}.MeasurementTVP.metadata.TVPMeasurementMetadata.qualifier{}.Text.quality{}.Category.constraint.AllowedTokens.id xml_buffer, point{}.MeasurementTVP.metadata.TVPMeasurementMetadata.qualifier{}.Text.quality{}.Category.constraint.AllowedTokens.extension{} xml_xml,
      point{}.MeasurementTVP.metadata.TVPMeasurementMetadata.qualifier{}.Text.quality{}.Category.constraint.AllowedTokens.value{} xml_buffer, point{}.MeasurementTVP.metadata.TVPMeasurementMetadata.qualifier{}.Text.quality{}.Category.constraint.AllowedTokens.pattern xml_buffer, point{}.MeasurementTVP.metadata.TVPMeasurementMetadata.qualifier{}.Text.quality{}.Category.value xml_buffer, point{}.MeasurementTVP.metadata.TVPMeasurementMetadata.qualifier{}.Text.quality{}.Text xml_xml, point{}.MeasurementTVP.metadata.TVPMeasurementMetadata.qualifier{}.Text.quality{}.Text.referenceFrame xml_buffer, point{}.MeasurementTVP.metadata.TVPMeasurementMetadata.qualifier{}.Text.quality{}.Text.axisID xml_buffer, point{}.MeasurementTVP.metadata.TVPMeasurementMetadata.qualifier{}.Text.quality{}.Text.updatable xml_boolean, point{}.MeasurementTVP.metadata.TVPMeasurementMetadata.qualifier{}.Text.quality{}.Text.optional xml_boolean, point{}.MeasurementTVP.metadata.TVPMeasurementMetadata.qualifier{}.Text.quality{}.Text.definition xml_buffer, point{}.MeasurementTVP.metadata.TVPMeasurementMetadata.qualifier{}.Text.quality{}.Text.id xml_buffer, point{}.MeasurementTVP.metadata.TVPMeasurementMetadata.qualifier{}.Text.nilValues.xlink_href xml_buffer, point{}.MeasurementTVP.metadata.TVPMeasurementMetadata.qualifier{}.Text.nilValues.xlink_title xml_buffer, point{}.MeasurementTVP.metadata.TVPMeasurementMetadata.qualifier{}.Text.nilValues.NilValues.id xml_buffer, point{}.MeasurementTVP.metadata.TVPMeasurementMetadata.qualifier{}.Text.nilValues.NilValues.extension{} xml_xml, point{}.MeasurementTVP.metadata.TVPMeasurementMetadata.qualifier{}.Text.nilValues.NilValues.nilValue{} xml_buffer, point{}.MeasurementTVP.metadata.TVPMeasurementMetadata.qualifier{}.Text.nilValues.NilValues.nilValue{}.reason xml_buffer, point{}.MeasurementTVP.metadata.TVPMeasurementMetadata.qualifier{}.Text.constraint.xlink_href xml_buffer, point{}.MeasurementTVP.metadata.TVPMeasurementMetadata.qualifier{}.Text.constraint.xlink_title xml_buffer, point{}.MeasurementTVP.metadata.TVPMeasurementMetadata.qualifier{}.Text.constraint.AllowedTokens.id xml_buffer, point{}.MeasurementTVP.metadata.TVPMeasurementMetadata.qualifier{}.Text.constraint.AllowedTokens.extension{} xml_xml, point{}.MeasurementTVP.metadata.TVPMeasurementMetadata.qualifier{}.Text.constraint.AllowedTokens.value{} xml_buffer, point{}.MeasurementTVP.metadata.TVPMeasurementMetadata.qualifier{}.Text.constraint.AllowedTokens.pattern xml_buffer, point{}.MeasurementTVP.metadata.TVPMeasurementMetadata.qualifier{}.Text.value xml_buffer, point{}.MeasurementTVP.metadata.TVPMeasurementMetadata.processing.owns xml_boolean, point{}.MeasurementTVP.metadata.TVPMeasurementMetadata.processing.nilReason xml_buffer, point{}.MeasurementTVP.metadata.TVPMeasurementMetadata.processing.gml_remoteSchema xml_buffer, point{}.MeasurementTVP.metadata.TVPMeasurementMetadata.processing.xlink_href xml_buffer, point{}.MeasurementTVP.metadata.TVPMeasurementMetadata.processing.xlink_title xml_buffer, point{}.MeasurementTVP.metadata.TVPMeasurementMetadata.source.owns xml_boolean, point{}.MeasurementTVP.metadata.TVPMeasurementMetadata.source.nilReason xml_buffer,
      point{}.MeasurementTVP.metadata.TVPMeasurementMetadata.source.gml_remoteSchema xml_buffer, point{}.MeasurementTVP.metadata.TVPMeasurementMetadata.source.xlink_href xml_buffer, point{}.MeasurementTVP.metadata.TVPMeasurementMetadata.source.xlink_title xml_buffer, point{}.MeasurementTVP.metadata.TVPMeasurementMetadata.uom.code xml_buffer, point{}.MeasurementTVP.metadata.TVPMeasurementMetadata.uom.xlink_href xml_buffer, point{}.MeasurementTVP.metadata.TVPMeasurementMetadata.uom.xlink_title xml_buffer, point{}.MeasurementTVP.metadata.TVPMeasurementMetadata.interpolationType.owns xml_boolean, point{}.MeasurementTVP.metadata.TVPMeasurementMetadata.interpolationType.nilReason xml_buffer, point{}.MeasurementTVP.metadata.TVPMeasurementMetadata.interpolationType.gml_remoteSchema xml_buffer, point{}.MeasurementTVP.metadata.TVPMeasurementMetadata.interpolationType.xlink_href xml_buffer, point{}.MeasurementTVP.metadata.TVPMeasurementMetadata.interpolationType.xlink_title xml_buffer, point{}.MeasurementTVP.metadata.TVPMeasurementMetadata.censoredReason.owns xml_boolean, point{}.MeasurementTVP.metadata.TVPMeasurementMetadata.censoredReason.nilReason xml_buffer, point{}.MeasurementTVP.metadata.TVPMeasurementMetadata.censoredReason.gml_remoteSchema xml_buffer, point{}.MeasurementTVP.metadata.TVPMeasurementMetadata.censoredReason.xlink_href xml_buffer, point{}.MeasurementTVP.metadata.TVPMeasurementMetadata.censoredReason.xlink_title xml_buffer, point{}.MeasurementTVP.metadata.TVPMeasurementMetadata.accuracy.xlink_href xml_buffer, point{}.MeasurementTVP.metadata.TVPMeasurementMetadata.accuracy.xlink_title xml_buffer, point{}.MeasurementTVP.metadata.TVPMeasurementMetadata.accuracy.Quantity.referenceFrame xml_buffer, point{}.MeasurementTVP.metadata.TVPMeasurementMetadata.accuracy.Quantity.axisID xml_buffer, point{}.MeasurementTVP.metadata.TVPMeasurementMetadata.accuracy.Quantity.updatable xml_boolean, point{}.MeasurementTVP.metadata.TVPMeasurementMetadata.accuracy.Quantity.optional xml_boolean, point{}.MeasurementTVP.metadata.TVPMeasurementMetadata.accuracy.Quantity.definition xml_buffer, point{}.MeasurementTVP.metadata.TVPMeasurementMetadata.accuracy.Quantity.id xml_buffer, point{}.MeasurementTVP.metadata.TVPMeasurementMetadata.accuracy.Quantity.extension{} xml_xml, point{}.MeasurementTVP.metadata.TVPMeasurementMetadata.accuracy.Quantity.identifier xml_buffer, point{}.MeasurementTVP.metadata.TVPMeasurementMetadata.accuracy.Quantity.label xml_buffer, point{}.MeasurementTVP.metadata.TVPMeasurementMetadata.accuracy.Quantity.description xml_buffer, point{}.MeasurementTVP.metadata.TVPMeasurementMetadata.accuracy.Quantity.quality{}.xlink_href xml_buffer, point{}.MeasurementTVP.metadata.TVPMeasurementMetadata.accuracy.Quantity.quality{}.xlink_title xml_buffer,
      point{}.MeasurementTVP.metadata.TVPMeasurementMetadata.accuracy.Quantity.quality{}.Quantity xml_xml, point{}.MeasurementTVP.metadata.TVPMeasurementMetadata.accuracy.Quantity.quality{}.Quantity.referenceFrame xml_buffer, point{}.MeasurementTVP.metadata.TVPMeasurementMetadata.accuracy.Quantity.quality{}.Quantity.axisID xml_buffer, point{}.MeasurementTVP.metadata.TVPMeasurementMetadata.accuracy.Quantity.quality{}.Quantity.updatable xml_boolean, point{}.MeasurementTVP.metadata.TVPMeasurementMetadata.accuracy.Quantity.quality{}.Quantity.optional xml_boolean, point{}.MeasurementTVP.metadata.TVPMeasurementMetadata.accuracy.Quantity.quality{}.Quantity.definition xml_buffer, point{}.MeasurementTVP.metadata.TVPMeasurementMetadata.accuracy.Quantity.quality{}.Quantity.id xml_buffer, point{}.MeasurementTVP.metadata.TVPMeasurementMetadata.accuracy.Quantity.quality{}.QuantityRange.referenceFrame xml_buffer, point{}.MeasurementTVP.metadata.TVPMeasurementMetadata.accuracy.Quantity.quality{}.QuantityRange.axisID xml_buffer, point{}.MeasurementTVP.metadata.TVPMeasurementMetadata.accuracy.Quantity.quality{}.QuantityRange.updatable xml_boolean, point{}.MeasurementTVP.metadata.TVPMeasurementMetadata.accuracy.Quantity.quality{}.QuantityRange.optional xml_boolean, point{}.MeasurementTVP.metadata.TVPMeasurementMetadata.accuracy.Quantity.quality{}.QuantityRange.definition xml_buffer, point{}.MeasurementTVP.metadata.TVPMeasurementMetadata.accuracy.Quantity.quality{}.QuantityRange.id xml_buffer, point{}.MeasurementTVP.metadata.TVPMeasurementMetadata.accuracy.Quantity.quality{}.QuantityRange.extension{} xml_xml, point{}.MeasurementTVP.metadata.TVPMeasurementMetadata.accuracy.Quantity.quality{}.QuantityRange.identifier xml_buffer, point{}.MeasurementTVP.metadata.TVPMeasurementMetadata.accuracy.Quantity.quality{}.QuantityRange.label xml_buffer, point{}.MeasurementTVP.metadata.TVPMeasurementMetadata.accuracy.Quantity.quality{}.QuantityRange.description xml_buffer, point{}.MeasurementTVP.metadata.TVPMeasurementMetadata.accuracy.Quantity.quality{}.QuantityRange.quality{} xml_xml, point{}.MeasurementTVP.metadata.TVPMeasurementMetadata.accuracy.Quantity.quality{}.QuantityRange.quality{}.xlink_href xml_buffer, point{}.MeasurementTVP.metadata.TVPMeasurementMetadata.accuracy.Quantity.quality{}.QuantityRange.quality{}.xlink_title xml_buffer, point{}.MeasurementTVP.metadata.TVPMeasurementMetadata.accuracy.Quantity.quality{}.QuantityRange.nilValues.xlink_href xml_buffer, point{}.MeasurementTVP.metadata.TVPMeasurementMetadata.accuracy.Quantity.quality{}.QuantityRange.nilValues.xlink_title xml_buffer, point{}.MeasurementTVP.metadata.TVPMeasurementMetadata.accuracy.Quantity.quality{}.QuantityRange.nilValues.NilValues.id xml_buffer, point{}.MeasurementTVP.metadata.TVPMeasurementMetadata.accuracy.Quantity.quality{}.QuantityRange.nilValues.NilValues.extension{} xml_xml, point{}.MeasurementTVP.metadata.TVPMeasurementMetadata.accuracy.Quantity.quality{}.QuantityRange.nilValues.NilValues.nilValue{} xml_buffer, point{}.MeasurementTVP.metadata.TVPMeasurementMetadata.accuracy.Quantity.quality{}.QuantityRange.nilValues.NilValues.nilValue{}.reason xml_buffer, point{}.MeasurementTVP.metadata.TVPMeasurementMetadata.accuracy.Quantity.quality{}.QuantityRange.uom.code xml_buffer, point{}.MeasurementTVP.metadata.TVPMeasurementMetadata.accuracy.Quantity.quality{}.QuantityRange.uom.xlink_href xml_buffer, point{}.MeasurementTVP.metadata.TVPMeasurementMetadata.accuracy.Quantity.quality{}.QuantityRange.uom.xlink_title xml_buffer, point{}.MeasurementTVP.metadata.TVPMeasurementMetadata.accuracy.Quantity.quality{}.QuantityRange.constraint.xlink_href xml_buffer,
      point{}.MeasurementTVP.metadata.TVPMeasurementMetadata.accuracy.Quantity.quality{}.QuantityRange.constraint.xlink_title xml_buffer, point{}.MeasurementTVP.metadata.TVPMeasurementMetadata.accuracy.Quantity.quality{}.QuantityRange.constraint.AllowedValues.id xml_buffer, point{}.MeasurementTVP.metadata.TVPMeasurementMetadata.accuracy.Quantity.quality{}.QuantityRange.constraint.AllowedValues.extension{} xml_xml, point{}.MeasurementTVP.metadata.TVPMeasurementMetadata.accuracy.Quantity.quality{}.QuantityRange.constraint.AllowedValues.value{} xml_real64, point{}.MeasurementTVP.metadata.TVPMeasurementMetadata.accuracy.Quantity.quality{}.QuantityRange.constraint.AllowedValues.interval{} xml_buffer, point{}.MeasurementTVP.metadata.TVPMeasurementMetadata.accuracy.Quantity.quality{}.QuantityRange.constraint.AllowedValues.significantFigures xml_int64, point{}.MeasurementTVP.metadata.TVPMeasurementMetadata.accuracy.Quantity.quality{}.QuantityRange.value xml_buffer, point{}.MeasurementTVP.metadata.TVPMeasurementMetadata.accuracy.Quantity.quality{}.Category.referenceFrame xml_buffer, point{}.MeasurementTVP.metadata.TVPMeasurementMetadata.accuracy.Quantity.quality{}.Category.axisID xml_buffer, point{}.MeasurementTVP.metadata.TVPMeasurementMetadata.accuracy.Quantity.quality{}.Category.updatable xml_boolean, point{}.MeasurementTVP.metadata.TVPMeasurementMetadata.accuracy.Quantity.quality{}.Category.optional xml_boolean, point{}.MeasurementTVP.metadata.TVPMeasurementMetadata.accuracy.Quantity.quality{}.Category.definition xml_buffer, point{}.MeasurementTVP.metadata.TVPMeasurementMetadata.accuracy.Quantity.quality{}.Category.id xml_buffer, point{}.MeasurementTVP.metadata.TVPMeasurementMetadata.accuracy.Quantity.quality{}.Category.extension{} xml_xml, point{}.MeasurementTVP.metadata.TVPMeasurementMetadata.accuracy.Quantity.quality{}.Category.identifier xml_buffer, point{}.MeasurementTVP.metadata.TVPMeasurementMetadata.accuracy.Quantity.quality{}.Category.label xml_buffer, point{}.MeasurementTVP.metadata.TVPMeasurementMetadata.accuracy.Quantity.quality{}.Category.description xml_buffer, point{}.MeasurementTVP.metadata.TVPMeasurementMetadata.accuracy.Quantity.quality{}.Category.quality{} xml_xml, point{}.MeasurementTVP.metadata.TVPMeasurementMetadata.accuracy.Quantity.quality{}.Category.quality{}.xlink_href xml_buffer, point{}.MeasurementTVP.metadata.TVPMeasurementMetadata.accuracy.Quantity.quality{}.Category.quality{}.xlink_title xml_buffer, point{}.MeasurementTVP.metadata.TVPMeasurementMetadata.accuracy.Quantity.quality{}.Category.nilValues.xlink_href xml_buffer, point{}.MeasurementTVP.metadata.TVPMeasurementMetadata.accuracy.Quantity.quality{}.Category.nilValues.xlink_title xml_buffer, point{}.MeasurementTVP.metadata.TVPMeasurementMetadata.accuracy.Quantity.quality{}.Category.nilValues.NilValues.id xml_buffer, point{}.MeasurementTVP.metadata.TVPMeasurementMetadata.accuracy.Quantity.quality{}.Category.nilValues.NilValues.extension{} xml_xml, point{}.MeasurementTVP.metadata.TVPMeasurementMetadata.accuracy.Quantity.quality{}.Category.nilValues.NilValues.nilValue{} xml_buffer, point{}.MeasurementTVP.metadata.TVPMeasurementMetadata.accuracy.Quantity.quality{}.Category.nilValues.NilValues.nilValue{}.reason xml_buffer, point{}.MeasurementTVP.metadata.TVPMeasurementMetadata.accuracy.Quantity.quality{}.Category.codeSpace.xlink_href xml_buffer, point{}.MeasurementTVP.metadata.TVPMeasurementMetadata.accuracy.Quantity.quality{}.Category.codeSpace.xlink_title xml_buffer, point{}.MeasurementTVP.metadata.TVPMeasurementMetadata.accuracy.Quantity.quality{}.Category.constraint.xlink_href xml_buffer, point{}.MeasurementTVP.metadata.TVPMeasurementMetadata.accuracy.Quantity.quality{}.Category.constraint.xlink_title xml_buffer,
      point{}.MeasurementTVP.metadata.TVPMeasurementMetadata.accuracy.Quantity.quality{}.Category.constraint.AllowedTokens.id xml_buffer, point{}.MeasurementTVP.metadata.TVPMeasurementMetadata.accuracy.Quantity.quality{}.Category.constraint.AllowedTokens.extension{} xml_xml, point{}.MeasurementTVP.metadata.TVPMeasurementMetadata.accuracy.Quantity.quality{}.Category.constraint.AllowedTokens.value{} xml_buffer, point{}.MeasurementTVP.metadata.TVPMeasurementMetadata.accuracy.Quantity.quality{}.Category.constraint.AllowedTokens.pattern xml_buffer, point{}.MeasurementTVP.metadata.TVPMeasurementMetadata.accuracy.Quantity.quality{}.Category.value xml_buffer, point{}.MeasurementTVP.metadata.TVPMeasurementMetadata.accuracy.Quantity.quality{}.Text.referenceFrame xml_buffer, point{}.MeasurementTVP.metadata.TVPMeasurementMetadata.accuracy.Quantity.quality{}.Text.axisID xml_buffer, point{}.MeasurementTVP.metadata.TVPMeasurementMetadata.accuracy.Quantity.quality{}.Text.updatable xml_boolean, point{}.MeasurementTVP.metadata.TVPMeasurementMetadata.accuracy.Quantity.quality{}.Text.optional xml_boolean, point{}.MeasurementTVP.metadata.TVPMeasurementMetadata.accuracy.Quantity.quality{}.Text.definition xml_buffer, point{}.MeasurementTVP.metadata.TVPMeasurementMetadata.accuracy.Quantity.quality{}.Text.id xml_buffer, point{}.MeasurementTVP.metadata.TVPMeasurementMetadata.accuracy.Quantity.quality{}.Text.extension{} xml_xml, point{}.MeasurementTVP.metadata.TVPMeasurementMetadata.accuracy.Quantity.quality{}.Text.identifier xml_buffer, point{}.MeasurementTVP.metadata.TVPMeasurementMetadata.accuracy.Quantity.quality{}.Text.label xml_buffer, point{}.MeasurementTVP.metadata.TVPMeasurementMetadata.accuracy.Quantity.quality{}.Text.description xml_buffer, point{}.MeasurementTVP.metadata.TVPMeasurementMetadata.accuracy.Quantity.quality{}.Text.quality{} xml_xml, point{}.MeasurementTVP.metadata.TVPMeasurementMetadata.accuracy.Quantity.quality{}.Text.quality{}.xlink_href xml_buffer, point{}.MeasurementTVP.metadata.TVPMeasurementMetadata.accuracy.Quantity.quality{}.Text.quality{}.xlink_title xml_buffer, point{}.MeasurementTVP.metadata.TVPMeasurementMetadata.accuracy.Quantity.quality{}.Text.nilValues.xlink_href xml_buffer, point{}.MeasurementTVP.metadata.TVPMeasurementMetadata.accuracy.Quantity.quality{}.Text.nilValues.xlink_title xml_buffer, point{}.MeasurementTVP.metadata.TVPMeasurementMetadata.accuracy.Quantity.quality{}.Text.nilValues.NilValues.id xml_buffer, point{}.MeasurementTVP.metadata.TVPMeasurementMetadata.accuracy.Quantity.quality{}.Text.nilValues.NilValues.extension{} xml_xml, point{}.MeasurementTVP.metadata.TVPMeasurementMetadata.accuracy.Quantity.quality{}.Text.nilValues.NilValues.nilValue{} xml_buffer, point{}.MeasurementTVP.metadata.TVPMeasurementMetadata.accuracy.Quantity.quality{}.Text.nilValues.NilValues.nilValue{}.reason xml_buffer, point{}.MeasurementTVP.metadata.TVPMeasurementMetadata.accuracy.Quantity.quality{}.Text.constraint.xlink_href xml_buffer, point{}.MeasurementTVP.metadata.TVPMeasurementMetadata.accuracy.Quantity.quality{}.Text.constraint.xlink_title xml_buffer, point{}.MeasurementTVP.metadata.TVPMeasurementMetadata.accuracy.Quantity.quality{}.Text.constraint.AllowedTokens.id xml_buffer, point{}.MeasurementTVP.metadata.TVPMeasurementMetadata.accuracy.Quantity.quality{}.Text.constraint.AllowedTokens.extension{} xml_xml, point{}.MeasurementTVP.metadata.TVPMeasurementMetadata.accuracy.Quantity.quality{}.Text.constraint.AllowedTokens.value{} xml_buffer, point{}.MeasurementTVP.metadata.TVPMeasurementMetadata.accuracy.Quantity.quality{}.Text.constraint.AllowedTokens.pattern xml_buffer,
      point{}.MeasurementTVP.metadata.TVPMeasurementMetadata.accuracy.Quantity.quality{}.Text.value xml_buffer, point{}.MeasurementTVP.metadata.TVPMeasurementMetadata.accuracy.Quantity.nilValues.xlink_href xml_buffer, point{}.MeasurementTVP.metadata.TVPMeasurementMetadata.accuracy.Quantity.nilValues.xlink_title xml_buffer, point{}.MeasurementTVP.metadata.TVPMeasurementMetadata.accuracy.Quantity.nilValues.NilValues.id xml_buffer, point{}.MeasurementTVP.metadata.TVPMeasurementMetadata.accuracy.Quantity.nilValues.NilValues.extension{} xml_xml, point{}.MeasurementTVP.metadata.TVPMeasurementMetadata.accuracy.Quantity.nilValues.NilValues.nilValue{} xml_buffer, point{}.MeasurementTVP.metadata.TVPMeasurementMetadata.accuracy.Quantity.nilValues.NilValues.nilValue{}.reason xml_buffer, point{}.MeasurementTVP.metadata.TVPMeasurementMetadata.accuracy.Quantity.uom.code xml_buffer, point{}.MeasurementTVP.metadata.TVPMeasurementMetadata.accuracy.Quantity.uom.xlink_href xml_buffer, point{}.MeasurementTVP.metadata.TVPMeasurementMetadata.accuracy.Quantity.uom.xlink_title xml_buffer, point{}.MeasurementTVP.metadata.TVPMeasurementMetadata.accuracy.Quantity.constraint.xlink_href xml_buffer, point{}.MeasurementTVP.metadata.TVPMeasurementMetadata.accuracy.Quantity.constraint.xlink_title xml_buffer, point{}.MeasurementTVP.metadata.TVPMeasurementMetadata.accuracy.Quantity.constraint.AllowedValues.id xml_buffer, point{}.MeasurementTVP.metadata.TVPMeasurementMetadata.accuracy.Quantity.constraint.AllowedValues.extension{} xml_xml, point{}.MeasurementTVP.metadata.TVPMeasurementMetadata.accuracy.Quantity.constraint.AllowedValues.value{} xml_real64, point{}.MeasurementTVP.metadata.TVPMeasurementMetadata.accuracy.Quantity.constraint.AllowedValues.interval{} xml_buffer, point{}.MeasurementTVP.metadata.TVPMeasurementMetadata.accuracy.Quantity.constraint.AllowedValues.significantFigures xml_int64, point{}.MeasurementTVP.metadata.TVPMeasurementMetadata.accuracy.Quantity.value xml_real64, point{}.MeasurementTVP.metadata.TVPMeasurementMetadata.aggregationDuration xml_buffer
    -> ListExploder
ListExploder
    ATTR_ACCUM_MODE = Merge List Attributes
    ATTR_CONFLICT_RES = Use List Attribute Values
    INDEX_ATTR = _element_index
    LIST_ATTR = point{}
    ELEMENTS -> Sampler
Sampler
    GROUP_BY = gml_parent_id
    RATE = 1
    SAMPLE_MODE = No
    SAMPLE_TYPE_LONG = Last N Features
    SAMPLED -> SubstringExtractor_2
SubstringExtractor_2
    END = 15
    RESULT_ATTR = stationID
    SRC_STRING = @Value(gml_id)
    START = 8
    -> AttributeManager_2
AttributeManager_2
    ATTR_TABLE:
      RENAME_SET_VALUE MeasurementTVP.time > time
      RENAME_SET_VALUE MeasurementTVP.value > flow
      REMOVE gml_parent_id
      REMOVE gml_parent_property
      REMOVE gml_id
      REMOVE _element_index
      RENAME_SET_VALUE stationID > gauge_id
    -> FeatureJoiner [LEFT]
MonitoringPoint (reader GML_1)
    attributes: type.owns xml_boolean, type.nilReason xml_buffer, type.gml_remoteSchema xml_buffer, type.xlink_href xml_buffer, type.xlink_title xml_buffer, sampledFeature.owns xml_boolean, sampledFeature.nilReason xml_buffer, sampledFeature.gml_remoteSchema xml_buffer, sampledFeature.xlink_href xml_buffer, sampledFeature.xlink_title xml_buffer, sampledFeature.xsi_nil xml_boolean, lineage xml_xml, lineage.nilReason xml_buffer, lineage.uuidref xml_buffer, lineage.xlink_href xml_buffer, lineage.xlink_title xml_buffer, relatedObservation{}.nilReason xml_buffer, relatedObservation{}.gml_remoteSchema xml_buffer, relatedObservation{}.xlink_href xml_buffer, relatedObservation{}.xlink_title xml_buffer, relatedSamplingFeature{}.SamplingFeatureComplex.role.owns xml_boolean, relatedSamplingFeature{}.SamplingFeatureComplex.role.nilReason xml_buffer, relatedSamplingFeature{}.SamplingFeatureComplex.role.gml_remoteSchema xml_buffer, relatedSamplingFeature{}.SamplingFeatureComplex.role.xlink_href xml_buffer, relatedSamplingFeature{}.SamplingFeatureComplex.role.xlink_title xml_buffer, relatedSamplingFeature{}.SamplingFeatureComplex.relatedSamplingFeature.nilReason xml_buffer, relatedSamplingFeature{}.SamplingFeatureComplex.relatedSamplingFeature.gml_remoteSchema xml_buffer, relatedSamplingFeature{}.SamplingFeatureComplex.relatedSamplingFeature.xlink_href xml_buffer, relatedSamplingFeature{}.SamplingFeatureComplex.relatedSamplingFeature.xlink_title xml_buffer, parameter{}.nilReason xml_buffer,
      parameter{}.gml_remoteSchema xml_buffer, parameter{}.xlink_href xml_buffer, parameter{}.xlink_title xml_buffer, parameter{}.NamedValue.name.owns xml_boolean, parameter{}.NamedValue.name.nilReason xml_buffer, parameter{}.NamedValue.name.gml_remoteSchema xml_buffer, parameter{}.NamedValue.name.xlink_href xml_buffer, parameter{}.NamedValue.name.xlink_title xml_buffer, parameter{}.NamedValue.value xml_xml, hostedProcedure{} xml_xml, hostedProcedure{}.nilReason xml_buffer, hostedProcedure{}.gml_remoteSchema xml_buffer, hostedProcedure{}.xlink_href xml_buffer, hostedProcedure{}.xlink_title xml_buffer, positionalAccuracy{} xml_xml, positionalAccuracy{}.nilReason xml_buffer, positionalAccuracy{}.uuidref xml_buffer, positionalAccuracy{}.xlink_href xml_buffer, positionalAccuracy{}.xlink_title xml_buffer, shape xml_geometry, relatedParty{} xml_xml, relatedParty{}.nilReason xml_buffer, relatedParty{}.uuidref xml_buffer, relatedParty{}.xlink_href xml_buffer, relatedParty{}.xlink_title xml_buffer, monitoringType{}.owns xml_boolean, monitoringType{}.nilReason xml_buffer, monitoringType{}.gml_remoteSchema xml_buffer, monitoringType{}.xlink_href xml_buffer, monitoringType{}.xlink_title xml_buffer,
      descriptionReference{}.owns xml_boolean, descriptionReference{}.nilReason xml_buffer, descriptionReference{}.gml_remoteSchema xml_buffer, descriptionReference{}.xlink_href xml_buffer, descriptionReference{}.xlink_title xml_buffer, verticalDatum{} xml_xml, verticalDatum{}.nilReason xml_buffer, verticalDatum{}.gml_remoteSchema xml_buffer, verticalDatum{}.xlink_href xml_buffer, verticalDatum{}.xlink_title xml_buffer, timeZone.owns xml_boolean, timeZone.TimeZone.zoneOffset xml_buffer, timeZone.TimeZone.zoneAbbreviation xml_buffer, daylightSavingTimeZone.owns xml_boolean, daylightSavingTimeZone.TimeZone.zoneOffset xml_buffer, daylightSavingTimeZone.TimeZone.zoneAbbreviation xml_buffer
    -> AttributeManager
AttributeManager
    ATTR_TABLE:
      RENAME_SET_VALUE sampledFeature.xlink_title > gnisname
      RENAME_SET_VALUE gml_parent_id > gauge_id
      REMOVE gml_parent_property
      REMOVE gml_id
    -> SubstringExtractor
SubstringExtractor
    END = 16
    RESULT_ATTR = gauge_id
    SRC_STRING = @Value(gauge_id)
    START = 9
    -> FeatureJoiner [RIGHT]
FeatureJoiner
    ATTR_CONFLICT_RES = Use Right
    GEOMETRY_HANDLING = Use Right
    JOIN_KEYS = gauge_id gauge_id AUTO
    JOIN_MODE = Inner
    JOINED -> gauge_readings (writer POSTGIS_1)
gauge_readings (writer POSTGIS_1)
    attributes: time timestamptz, flow float8, gauge_id varchar(200), gnisname varchar(200)
