FME workspace mapboxExport.fmw

Parameters:
- SourceDataset_POSTGIS_7 = postgres   # Connection

Readers:
- POSTGIS_2: POSTGIS from $(SourceDataset_POSTGIS_7)

Creator
    GEOMTYPE = Geometry Object
    NUM = 1
    CREATED -> FeatureReader [INITIATOR]
FeatureReader
    ATTRIBUTES = public.fme_gauge_export,"datasource,name,url,watersourcename,value,measure_time,minzoom",public.vw_all_rivers,"flow,gnis_name,difficulty_numeric,level,awid,difficulty,slope,hydroseq,zoom,totdasqkm",public.vw_putins,"difficulty_numeric,name,awid,level,recorddate,hydroseq,difficulty",public.youtube,videoid
    ATTR_ACCUM_MODE = Only Use Result
    COMBINE_GEOM = Use Result
    DATASET = postgres
    FEATURETYPES = public.fme_gauge_export public.vw_all_rivers public.vw_putins public.youtube
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = postgres
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    public.youtube -> FeatureWriter [public.youtube]
    public.vw_putins -> AttributeManager_2
    public.fme_gauge_export -> DateTimeConverter
    public.vw_all_rivers -> AttributeManager
JSONFormatter
    ERROR_LIST_ATTR = _json_error
    FORMAT = Pretty Print
    INDENT_STYLE = 3 spaces
    JSON_DOCUMENT = @Value(_result)
    OUTPUT_ATTR = text_line_data
    OUTPUT_ENCODING = UTF-8
    REMOVE_EMPTY_OBJECTS_AND_ARRAYS = No
    REMOVE_EMPTY_STRINGS = No
    REMOVE_NULLS = No
    -> FeatureWriter_2 [text_line]
FeatureWriter_2
    DATASET = /tmp/json/alldata.json
    DATASET_ATTR = _dataset
    FEATURE_TYPE_LIST_ATTR = _feature_type
    FORMAT = TEXTLINE
    TEXTLINE_COORDINATE_SYSTEM_GRANULARITY = FEATURE
    TEXTLINE_DESTINATION_DATASETTYPE_VALIDATION = Yes
    TEXTLINE_ENCODING = SYSTEM
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    SUMMARY -> SystemCaller
SystemCaller
    CMD = tippecanoe -o /tmp/json/alldata.mbtiles /tmp/json/alldata.json -f --simplification=10

Bookmark: Youtube video export
FeatureWriter
    DATASET = /tmp/json/videos.json
    DATASET_ATTR = _dataset
    FEATURE_TYPE_LIST_ATTR = _feature_type
    FORMAT = GEOJSON
    GEOJSON_COUNTER_CLOCKWISE_AREAS = Yes
    GEOJSON_DESTINATION_DATASETTYPE_VALIDATION = Yes
    GEOJSON_INDENT_SIZE = 0
    GEOJSON_MAX_COORDINATE_PRECISION = 10
    GEOJSON_PRETTY_PRINT = YES
    GEOJSON_STRICT_SPEC = Yes
    GEOJSON_WGS84_REPROJECTION = Yes
    GEOJSON_WRITER_CHARSET = UTF-8
    GEOJSON_WRITE_BOM = No
    TOTAL_FEATURES_WRITTEN_ATTR = _total_features_written

Bookmark: Put-in exports (includes current river level)
AttributeManager_2
    ATTR_TABLE = SET_TO difficulty_numeric = FME_CONDITIONAL:DEFAULT_VALUE'_FME_NO_OP_'BOOL_OP;OR;COMPOSITE_TEST;<Unused>;TEST difficulty_numeric ATTRIBUTE_VALUE_NULL _FME_BLANK_STRING_'-1'FME_NUM_CONDITIONS2___
    -> 2DForcer_3
2DForcer_3
    2D -> GeometryExtractor_3
GeometryExtractor_3
    ATTR = _geometry
    JSON_MAX_DIGITS = 7
    KIND_LONG = GeoJSON
    OGCVERSION = 1.2
    OGC_WKT_PRECISION_DISPLAY = 64-bit
    OGEOSMS_URL_PREFIX = http://maps.google.com/?q=
    PREFER_POLYGON_OVER_SURFACE = No
    REMOVE_GEOMETRY = No
    -> JSONTemplater_3 [ROOT]
JSONTemplater_3
    RESULT_ATTRIBUTE = _result
    ROOT_QUERY_EXPR:
        {
          "type" : "Feature",
          "tippecanoe" : {
              "minzoom" : 4,
              "layer" : 'putins'

          },
          "properties" : {
              "name" : fme:get-attribute("name") ,
              "level" : fme:get-attribute("level") ,
              "awid" : fme:get-attribute("awid") ,
              "difficulty_numeric" : xs:int(fme:get-attribute("difficulty_numeric"))
          },
          "geometry" : fme:get-json-attribute("_geometry")
      }
    VISIBLE_QUERY_VALIDATE = Yes
    -> JSONFormatter
    -> JSONFormatter_2
JSONFormatter_2
    ERROR_LIST_ATTR = _json_error
    FORMAT = Pretty Print
    INDENT_STYLE = 3 spaces
    JSON_DOCUMENT = @Value(_result)
    OUTPUT_ATTR = _formatted
    OUTPUT_ENCODING = UTF-8
    REMOVE_EMPTY_OBJECTS_AND_ARRAYS = No
    REMOVE_EMPTY_STRINGS = No
    REMOVE_NULLS = No
    -> FeatureWriter_3 [text_line]
FeatureWriter_3
    DATASET = putins.json
    DATASET_ATTR = _dataset
    FEATURE_TYPE_LIST_ATTR = _feature_type
    FORMAT = TEXTLINE
    TEXTLINE_COORDINATE_SYSTEM_GRANULARITY = FEATURE
    TEXTLINE_DESTINATION_DATASETTYPE_VALIDATION = Yes
    TEXTLINE_ENCODING = SYSTEM
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written

Bookmark: Gauge exports
DateTimeConverter
    DATETIME_ATTR = measure_time
    IN_FORMAT = %Y%m%d%H%M%S
    OUT_FORMAT = FME
    REPAIR_INPUT = NO
    TEST_INPUT = 20180813181500-06:00
    -> DateTimeCalculator
DateTimeCalculator
    MODE = DATETIMECALC_3_CALCULATE_INTERVAL
    OPERATION_PARAMETERS = START_DATETIME]@Value(measure_time)]END_DATETIME]@DateTimeNow()]RESULT_TYPE]HOURS]RESULT_INTERVAL]timeSincePresent]FME_CONTROLLER_QUERY_FILE]transformers/dependencies/datetimecalculator/DATETIMECALC_3_CALCULATE_INTERVAL.fme
    -> 2DForcer_2
2DForcer_2
    2D -> GeometryExtractor_2
GeometryExtractor_2
    ATTR = _geometry
    JSON_MAX_DIGITS = 7
    KIND_LONG = GeoJSON
    OGCVERSION = 1.2
    OGC_WKT_PRECISION_DISPLAY = 64-bit
    OGEOSMS_URL_PREFIX = http://maps.google.com/?q=
    PREFER_POLYGON_OVER_SURFACE = No
    REMOVE_GEOMETRY = No
    -> JSONTemplater_2 [ROOT]
JSONTemplater_2
    RESULT_ATTRIBUTE = _result
    ROOT_QUERY_EXPR:
        {
          "type" : "Feature",
          "tippecanoe" : {
              "minzoom" : fme:get-attribute("minzoom"),
              "layer" : 'gauge'
          },
          "properties" : {
              "name" : fme:get-attribute("name") ,
              "timeSincePresent": fme:get-attribute("timeSincePresent"),
              "url" : fme:get-attribute("url"),
              "value" : fme:get-attribute("value")
          },
          "geometry" : fme:get-json-attribute("_geometry")
      }
    VISIBLE_QUERY_VALIDATE = Yes
    -> JSONFormatter

Bookmark: Rivers over 50,000 cfs
AttributeManager
    ATTR_TABLE:
      SET_TO flow = FME_CONDITIONAL:DEFAULT_VALUE'_FME_NO_OP_'BOOL_OP;OR;COMPOSITE_TEST;<Unused>;TEST flow ATTRIBUTE_VALUE_NULL _FME_BLANK_STRING_'0'FME_NUM_CONDITIONS2___
      SET_TO difficulty_numeric = FME_CONDITIONAL:DEFAULT_VALUE'_FME_NO_OP_'BOOL_OP;OR;COMPOSITE_TEST;<Unused>;TEST difficulty_numeric ATTRIBUTE_VALUE_NULL _FME_BLANK_STRING_'-1'FME_NUM_CONDITIONS2___
      SET_TO rivertype = FME_CONDITIONAL:DEFAULT_VALUE'rivers-nonww'BOOL_OP;OR;COMPOSITE_TEST;<Unused>;TEST @Value(level) = med;TEST @Value(level) = high'rivers-running'BOOL_OP;OR;COMPOSITE_TEST;<Unused>;TEST awid ATTRIBUTE_HAS_A_VALUE _FME_BLANK_STRING_'rivers-dry'FME_NUM_CONDITIONS3___
      SET_TO zoom = FME_CONDITIONAL:DEFAULT_VALUE'@Evaluate(@round(@sub(11,@mult(@pow(@min(1,@Value(totdasqkm)/50000),0.5),7))))'BOOL_OP;OR;COMPOSITE_TEST;<Unused>;TEST awid ATTRIBUTE_HAS_A_VALUE _FME_BLANK_STRING_'7'FME_NUM_CONDITIONS2___
    -> 2DForcer
2DForcer
    2D -> GeometryExtractor
GeometryExtractor
    ATTR = _geometry
    JSON_MAX_DIGITS = 7
    KIND_LONG = GeoJSON
    OGCVERSION = 1.2
    OGC_WKT_PRECISION_DISPLAY = 64-bit
    OGEOSMS_URL_PREFIX = http://maps.google.com/?q=
    PREFER_POLYGON_OVER_SURFACE = No
    REMOVE_GEOMETRY = No
    -> JSONTemplater [ROOT]
JSONTemplater
    RESULT_ATTRIBUTE = _result
    ROOT_QUERY_EXPR:
        {
          "type" : "Feature",
          "tippecanoe" : {
              "minzoom" : fme:get-attribute("zoom"),
              "layer" : fme:get-attribute("rivertype")
          },
          "properties" : {
              "awid" : fme:get-attribute("awid") ,
              "difficulty": fme:get-attribute("difficulty"),
              "difficulty_numeric" : xs:int(fme:get-attribute("difficulty_numeric")),
              "flow" : xs:int(fme:get-attribute("flow")),
              "gnis_name" : fme:get-attribute("gnis_name") ,
              "level": fme:get-attribute("level"),
              "rivertype" : fme:get-attribute("rivertype"),
              "slope" : fme:get-attribute("slope")
          },
          "geometry" : fme:get-json-attribute("_geometry")
      }
    VISIBLE_QUERY_VALIDATE = Yes
    -> JSONFormatter
