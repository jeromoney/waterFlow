FME workspace caDWRgaugereader.fmw

Parameters:
- SourceDataset_POSTGIS = flowdb   # Connection

Readers:
- POSTGIS_1: POSTGIS from $(SourceDataset_POSTGIS)

public.gauge (reader POSTGIS_1)
    attributes: watersource int4,BTree, datasource varchar(10),BTree, name varchar(100), url varchar(80), watersourcename varchar(80), id varchar(100),PrimaryKey, watershed char(2)
    -> HTTPCaller
HTTPCaller
    ADDITIONAL_URL_PARAMETERS = s;@Value(id)
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://cdec.water.ca.gov/dynamicapp/QueryF
    TRANSFER_TIMEOUT_LENGTH = 90
    USE_COOKIES = No
    VERIFY_SSL_CERTIFICATES = Yes
    -> HTMLExtractor
HTMLExtractor
    HTML_FIELD = @Value(_response_body)
    HTML_SPECIFICATION = Content
    RESULT_TYPE_NAME = LIST_ATTR
    SEARCH_TABLE = table table Whole
    Results -> ListExploder
ListExploder
    ATTR_ACCUM_MODE = Merge List Attributes
    ATTR_CONFLICT_RES = Use List Attribute Values
    INDEX_ATTR = _table_index
    LIST_ATTR = table{}
    ELEMENTS -> Tester
Tester
    BOOL_OP = AND
    TEST_CLAUSE = CASE_INSENSITIVE_TEST @Value(table) CONTAINS CFS
    PASSED -> HTMLExtractor_2
HTMLExtractor_2
    HTML_FIELD = @Value(table)
    HTML_SPECIFICATION = Content
    RESULT_TYPE_NAME = LIST_ATTR
    SEARCH_TABLE = record tr Value
    Results -> ListExploder_2
ListExploder_2
    ATTR_ACCUM_MODE = Merge List Attributes
    ATTR_CONFLICT_RES = Use List Attribute Values
    INDEX_ATTR = _record_index
    LIST_ATTR = record{}
    ELEMENTS -> Sampler
    ELEMENTS -> Sampler_2
Sampler
    GROUP_BY = id _table_index
    RATE = 1
    SAMPLE_MODE = No
    SAMPLE_TYPE_LONG = First N Features
    SAMPLED -> Inspector
Sampler_2
    GROUP_BY = id _table_index
    RATE = 1
    SAMPLE_MODE = No
    SAMPLE_TYPE_LONG = Last N Features
    SAMPLED -> Inspector
Inspector
