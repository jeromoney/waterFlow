FME workspace americanwhitewaterReader.fmw

Parameters:
- stateAbbrev = CA   # State abbreviation
- DestDataset_POSTGIS = postgres   # Connection
- DestDataset_POSTGRES = postgres   # Connection
- SourceDataset_POSTGRES = postgres   # Connection
- SourceDataset_OGCKML = http://www.americanwhitewater.org/content/River/state-summary/state/$(stateAbbrev)/.kml   # Source Google KML File or URL
- SourceDataset_POSTGIS_2 = postgres   # Connection

Readers:
- OGCKML_1: OGCKML from $(SourceDataset_OGCKML)
- POSTGRES_1: POSTGRES from $(SourceDataset_POSTGRES)
- POSTGIS_1: POSTGIS from $(SourceDataset_POSTGIS_2)

Writers:
- POSTGIS_2: POSTGIS to $(DestDataset_POSTGIS)
- POSTGRES_2: POSTGRES to $(DestDataset_POSTGRES)

Placemark (reader OGCKML_1)
    -> AttributeManager
AttributeManager
    ATTR_TABLE:
      RENAME_SET_VALUE kml_name > name
      RENAME_SET_VALUE kml_style_url > level
      RENAME_SET_VALUE kml_description > awid
      SET_TO state = $(stateAbbrev)
    -> StringReplacer
StringReplacer
    CASE = NO
    FIND_TEXT = #style_
    NO_MATCH = _FME_NO_OP_
    REGEXP = NO
    SRC_ATTRS = level
    -> StringSearcher
StringSearcher
    CASE = no
    MATCHED_RESULT_ATTR = awid
    REGEXP = (?<=detail/id/)\d+
    STRING_TO_SEARCH = @Value(awid)
    MATCHED -> UpdateDetector [Revised]
riverlevels (reader POSTGIS_1)
    attributes: name varchar(200), id int8,PrimaryKey, awid int4, hydroseq int4, difficulty varchar(10), difficulty_numeric int4, state varchar(2)
    -> UpdateDetector [Original]
UpdateDetector
    BLANK_AND_MISSING_DIFFER = No
    EXTRA_VERTEX_TOLERANCE = 0
    KEYATTR = awid
    LENIENT_MATCH = no
    MATCH = 2D
    MATCHATTRS = name state awid
    Updated -> Junction
    Inserted -> Junction
    Unchanged -> DateTimeStamper
Junction
    -> riverlevels (writer POSTGIS_2)
    -> DateTimeStamper
DateTimeStamper
    DATETIME_ATTR = recorddate
    INCLUDE_OFFSET = NO
    STAMP_TYPE = datetime
    TIMEZONE = utc
    -> AttributeManager_2
AttributeManager_2
    ATTR_TABLE:
      REMOVE name
      REMOVE id
      REMOVE hydroseq
      SET_TO recorddate = @TimeZoneSet(@Value(recorddate),utc)
    -> UpdateDetector_2 [Revised]
riverlevels (writer POSTGIS_2)
    attributes: name varchar(200), awid int4, state char(2)
riverlevels_data (reader POSTGRES_1)
    attributes: awid int4,PrimaryKey, level varchar(200), recorddate timestamptz
    -> UpdateDetector_2 [Original]
UpdateDetector_2
    BLANK_AND_MISSING_DIFFER = No
    EXTRA_VERTEX_TOLERANCE = 0
    KEYATTR = awid
    LENIENT_MATCH = no
    MATCH = 2D
    MATCHATTRS = level awid recorddate
    Updated -> riverlevels_data (writer POSTGRES_2)
    Inserted -> riverlevels_data (writer POSTGRES_2)
riverlevels_data (writer POSTGRES_2)
    attributes: awid int4,PrimaryKey, level varchar(200), recorddate timestamptz

FME custom transformer UpdateDetector
This transformer is based on the ChangeDetector and extends its functionality by adding an Updated output port. It detects changes between two sets of input features.
One set of features enters the transformer via the Original port. The other set enters via the Revised port. Both sets must have a key attribute, which will be used to compare them against each other.
An Original feature is output via the Unchanged port when it is found to have matching key attribute and either matching geometry, matching attribute values, or both, with a feature in the Revised set.
An Original feature is output via the Deleted port when no key attribute match for it can be found in the Revised set.
A Revised feature with no key attribute match in the Original set is output via the Inserted port.
A Revised feature with key attribute match in the Original set and has changes either in geometry, or attribute values, or both, is output via the Updated port.
Inserted, updated and deleted features will have fme_db_operation set to INSERT, UPDATE or DELETE respectively.
Please note that to get correct results, the key attribute must be provided to both "Key Attribute" and "Attribute(s) to match" parameter prompts. 
Connect the transformer in your workspace and set the required parameters.
If Lenient Geometry Matching is set to yes then the order of points in line and area features will be ignored.
If Treat Blank Value as Different From Missing Attribute is Yes, then an attribute will be considered different for two features when one feature contains the attribute with a blank value and the other feature does not contain the attribute at all.
When geometry is being matched, Extra Vertex Tolerance can allow for extra vertices along line segments. A value of 0 means that no such extra vertices are permitted. A nonzero value controls how close any extra vertices must be to the line connecting the adjoining matching vertices. Note: This setting has no effect when using lenient geometry matching.

Parameters:
- KEYATTR =   # " " Key Attribute
- MATCH = 2D   # Match Geometry
- LENIENT_MATCH = no   # Lenient Geometry Matching
- MATCHATTRS =   # " " Attributes to Match
- BLANK_AND_MISSING_DIFFER = No   # Treat Blank Value as Different From Missing Attribute
- EXTRA_VERTEX_TOLERANCE = 0   # Extra Vertex Tolerance (optional)

Original (input)
    -> ATTRIBUTECREATOR
Note: Created by Dmitri Bagh / February 03, 2006 / dmitri.bagh@safe.com
Revised (input)
    -> ATTRIBUTECREATOR_2
Note: All parameters / are published / to match functionality / of ChangeDetector
Note: UPDATEDETECTOR
ChangeDetector
    BLANK_AND_MISSING_DIFFER = $(BLANK_AND_MISSING_DIFFER)
    EXTRA_VERTEX_TOLERANCE = $(EXTRA_VERTEX_TOLERANCE)
    LENIENT_MATCH = $(LENIENT_MATCH)
    MATCH = $(MATCH)
    MATCHATTRS = $(MATCHATTRS)
    MATCH_STRATEGY = Match Selected Attributes
    UNCHANGED -> ATTRIBUTEREMOVER_3
    ADDED -> Matcher_2
    DELETED -> Matcher
Updated (output)
Inserted (output)
Unchanged (output)
Deleted (output)

Bookmark: OrigFlag Creators
  Assigning OrigFlag Y for original 
  features and N for revised.
  For further use in testers 
  after Matcher 
  where original and revised 
  feaures can be merged together.
ATTRIBUTECREATOR: AttributeCreator
    ATTR_TABLE = SET_TO OrigFlag = Y
    -> ChangeDetector [ORIGINAL]
    -> Matcher_2
ATTRIBUTECREATOR_2: AttributeCreator
    ATTR_TABLE = SET_TO OrigFlag = N
    -> ChangeDetector [REVISED]
    -> Matcher

Bookmark: Matchers
  Here published Key Attribute
  distinguishes between added 
  and modified (above), 
  and - between deleted 
  and modified (below)
Matcher_2
    BLANK_AND_MISSING_DIFFER = No
    CNT_ATTR = _match_id
    DIFFATTRS = OrigFlag
    LENIENT_MATCH = No
    MATCH = NONE
    MATCHATTRS = $(KEYATTR)
    MATCH_STRATEGY = Match Selected Attributes
    MATCHED -> TESTER
    NOT_MATCHED -> TESTER_2
Matcher
    BLANK_AND_MISSING_DIFFER = No
    CNT_ATTR = _match_id
    DIFFATTRS = OrigFlag
    LENIENT_MATCH = No
    MATCH = NONE
    MATCHATTRS = $(KEYATTR)
    MATCH_STRATEGY = Match Selected Attributes
    NOT_MATCHED -> TESTER_3

Bookmark: Testers
  For updated and added 
  we keep revised features
  For deleted - original features
TESTER: Tester
    BOOL_OP = OR
    TEST_CLAUSE = TEST @Value(OrigFlag) = N
    PASSED -> ATTRIBUTEREMOVER
TESTER_2: Tester
    BOOL_OP = OR
    TEST_CLAUSE = TEST @Value(OrigFlag) = N
    PASSED -> ATTRIBUTEREMOVER_2
TESTER_3: Tester
    BOOL_OP = OR
    TEST_CLAUSE = TEST @Value(OrigFlag) = Y
    PASSED -> ATTRIBUTEREMOVER_4

Bookmark: Deleting temp attributes
ATTRIBUTEREMOVER: AttributeRemover
    REMOVE_ATTRS = _match_id,OrigFlag
    -> AttributeCreator
ATTRIBUTEREMOVER_2: AttributeRemover
    REMOVE_ATTRS = _match_id,OrigFlag
    -> AttributeCreator_2
ATTRIBUTEREMOVER_3: AttributeRemover
    REMOVE_ATTRS = OrigFlag
    -> Unchanged (output)
ATTRIBUTEREMOVER_4: AttributeRemover
    REMOVE_ATTRS = _match_id,OrigFlag
    -> AttributeCreator_3

Bookmark: Add fme_db_operation attribute
AttributeCreator
    ATTR_TABLE = SET_TO fme_db_operation = UPDATE
    -> Updated (output)
AttributeCreator_2
    ATTR_TABLE = SET_TO fme_db_operation = INSERT
    -> Inserted (output)
AttributeCreator_3
    ATTR_TABLE = SET_TO fme_db_operation = DELETE
    -> Deleted (output)
