FME workspace index.fmw

Parameters:
- SourceDataset_CSV2_3 = http://dd.weather.gc.ca/hydrometric/doc/hydrometric_StationList.csv   # Source CSV (Comma Separated Value) File(s)
- SourceDataset_POSTGIS = flowdb   # Connection
- DestDataset_POSTGIS = flowdb   # Connection
- SourceDataset_POSTGRES = flowdb   # Connection

Readers:
- CSV2_1: CSV2 from $(SourceDataset_CSV2_3)
- POSTGIS_1: POSTGIS from $(SourceDataset_POSTGIS)
- POSTGRES_1: POSTGRES from $(SourceDataset_POSTGRES)

Writers:
- POSTGIS_3: POSTGIS to $(DestDataset_POSTGIS)

CSV (reader CSV2_1)
    attributes: ID string, Name / Nom string, Latitude string, Longitude string, Prov/Terr string, Timezone / Fuseau horaire string
    -> BulkAttributeRenamer
BulkAttributeRenamer
    ATTRCHOICE = All Attributes
    CASE_CHANGE_TYPE = lower
    MODE_CHOICE = RENAME
    PATTERN_ACTION_DISP = CASECHANGE
    -> VertexCreator
VertexCreator
    MODE_NAME = Add Point
    XVAL = @Value(longitude)
    YVAL = @Value(latitude)
    -> AttributeManager
AttributeManager
    ATTR_TABLE:
      RENAME_SET_VALUE  id > id
      RENAME_SET_VALUE name / nom > name
      REMOVE latitude
      REMOVE longitude
      SET_TO datasource = CANADA
      SET_TO url = https://wateroffice.ec.gc.ca/report/real_time_e.html?stn=@Value(id)
    -> CoordinateSystemSetter
CoordinateSystemSetter
    COORDSYS = EPSG:4326
    -> UpdateDetector [Revised]
public.gauge (reader POSTGIS_1)
    attributes: watersource int4,BTree, datasource varchar(10),BTree, name varchar(100), url varchar(80), watersourcename varchar(80), id varchar(100),PrimaryKey, watershed char(2)
    -> UpdateDetector [Original]
UpdateDetector
    BLANK_AND_MISSING_DIFFER = No
    EXTRA_VERTEX_TOLERANCE = 0
    KEYATTR = id
    LENIENT_MATCH = no
    MATCH = 2D
    MATCHATTRS = url id name
    Updated -> public.gauge (writer POSTGIS_3)
    Inserted -> public.gauge (writer POSTGIS_3)
public.gauge (writer POSTGIS_3)
    attributes: datasource varchar(10),BTree, name varchar(100), url varchar(80), id varchar(100),PrimaryKey
public.candianprovinceabbrev (reader POSTGRES_1)
    attributes: abbreviation text, english_name varchar(200), french_name varchar(200), source text
    -> WorkspaceRunner
WorkspaceRunner
    BLOCKING = Yes
    WORKSPACE_FILE = $(FME_MF_DIR)canada.fmw
    WORKSPACE_PARAMETERS = province,@Value(abbreviation)
    SUCCEEDED -> Logger
    FAILED -> Logger
    SUMMARY -> Logger
Logger
    LOG_FEATURE = LOG_ONLY
    MAXCOORDS = 20
    MAXFEATS = 20
    MESSAGE = Feature is:
    SEVERITY = INFO

FME custom transformer UpdateDetector
This transformer is based on the ChangeDetector and extends its functionality by adding an Updated output port. It detects changes between two sets of input features.
One set of features enters the transformer via the Original port. The other set enters via the Revised port. Both sets must have a key attribute, which will be used to compare them against each other.
An Original feature is output via the Unchanged port when it is found to have matching key attribute and either matching geometry, matching attribute values, or both, with a feature in the Revised set.
An Original feature is output via the Deleted port when no key attribute match for it can be found in the Revised set.
A Revised feature with no key attribute match in the Original set is output via the Inserted port.
A Revised feature with key attribute match in the Original set and has changes either in geometry, or attribute values, or both, is output via the Updated port.
Inserted, updated and deleted features will have fme_db_operation set to INSERT, UPDATE or DELETE respectively.
Please note that to get correct results, the key attribute must be provided to both "Key Attribute" and "Attribute(s) to match" parameter prompts. 
Connect the transformer in your workspace and set the required parameters.
If Lenient Geometry Matching is set to yes then the order of points in line and area features will be ignored.
If Treat Blank Value as Different From Missing Attribute is Yes, then an attribute will be considered different for two features when one feature contains the attribute with a blank value and the other feature does not contain the attribute at all.
When geometry is being matched, Extra Vertex Tolerance can allow for extra vertices along line segments. A value of 0 means that no such extra vertices are permitted. A nonzero value controls how close any extra vertices must be to the line connecting the adjoining matching vertices. Note: This setting has no effect when using lenient geometry matching.

Parameters:
- KEYATTR =   # " " Key Attribute
- MATCH = 2D   # Match Geometry
- LENIENT_MATCH = no   # Lenient Geometry Matching
- MATCHATTRS =   # " " Attributes to Match
- BLANK_AND_MISSING_DIFFER = No   # Treat Blank Value as Different From Missing Attribute
- EXTRA_VERTEX_TOLERANCE = 0   # Extra Vertex Tolerance (optional)

Original (input)
    -> ATTRIBUTECREATOR
Note: Created by Dmitri Bagh / February 03, 2006 / dmitri.bagh@safe.com
Revised (input)
    -> ATTRIBUTECREATOR_2
Note: All parameters / are published / to match functionality / of ChangeDetector
Note: UPDATEDETECTOR
ChangeDetector
    BLANK_AND_MISSING_DIFFER = $(BLANK_AND_MISSING_DIFFER)
    EXTRA_VERTEX_TOLERANCE = $(EXTRA_VERTEX_TOLERANCE)
    LENIENT_MATCH = $(LENIENT_MATCH)
    MATCH = $(MATCH)
    MATCHATTRS = $(MATCHATTRS)
    MATCH_STRATEGY = Match Selected Attributes
    UNCHANGED -> ATTRIBUTEREMOVER_3
    ADDED -> Matcher_2
    DELETED -> Matcher
Updated (output)
Inserted (output)
Unchanged (output)
Deleted (output)

Bookmark: OrigFlag Creators
  Assigning OrigFlag Y for original 
  features and N for revised.
  For further use in testers 
  after Matcher 
  where original and revised 
  feaures can be merged together.
ATTRIBUTECREATOR: AttributeCreator
    ATTR_TABLE = SET_TO OrigFlag = Y
    -> ChangeDetector [ORIGINAL]
    -> Matcher_2
ATTRIBUTECREATOR_2: AttributeCreator
    ATTR_TABLE = SET_TO OrigFlag = N
    -> ChangeDetector [REVISED]
    -> Matcher

Bookmark: Matchers
  Here published Key Attribute
  distinguishes between added 
  and modified (above), 
  and - between deleted 
  and modified (below)
Matcher_2
    BLANK_AND_MISSING_DIFFER = No
    CNT_ATTR = _match_id
    DIFFATTRS = OrigFlag
    LENIENT_MATCH = No
    MATCH = NONE
    MATCHATTRS = $(KEYATTR)
    MATCH_STRATEGY = Match Selected Attributes
    MATCHED -> TESTER
    NOT_MATCHED -> TESTER_2
Matcher
    BLANK_AND_MISSING_DIFFER = No
    CNT_ATTR = _match_id
    DIFFATTRS = OrigFlag
    LENIENT_MATCH = No
    MATCH = NONE
    MATCHATTRS = $(KEYATTR)
    MATCH_STRATEGY = Match Selected Attributes
    NOT_MATCHED -> TESTER_3

Bookmark: Testers
  For updated and added 
  we keep revised features
  For deleted - original features
TESTER: Tester
    BOOL_OP = OR
    TEST_CLAUSE = TEST @Value(OrigFlag) = N
    PASSED -> ATTRIBUTEREMOVER
TESTER_2: Tester
    BOOL_OP = OR
    TEST_CLAUSE = TEST @Value(OrigFlag) = N
    PASSED -> ATTRIBUTEREMOVER_2
TESTER_3: Tester
    BOOL_OP = OR
    TEST_CLAUSE = TEST @Value(OrigFlag) = Y
    PASSED -> ATTRIBUTEREMOVER_4

Bookmark: Deleting temp attributes
ATTRIBUTEREMOVER: AttributeRemover
    REMOVE_ATTRS = _match_id,OrigFlag
    -> AttributeCreator
ATTRIBUTEREMOVER_2: AttributeRemover
    REMOVE_ATTRS = _match_id,OrigFlag
    -> AttributeCreator_2
ATTRIBUTEREMOVER_3: AttributeRemover
    REMOVE_ATTRS = OrigFlag
    -> Unchanged (output)
ATTRIBUTEREMOVER_4: AttributeRemover
    REMOVE_ATTRS = _match_id,OrigFlag
    -> AttributeCreator_3

Bookmark: Add fme_db_operation attribute
AttributeCreator
    ATTR_TABLE = SET_TO fme_db_operation = UPDATE
    -> Updated (output)
AttributeCreator_2
    ATTR_TABLE = SET_TO fme_db_operation = INSERT
    -> Inserted (output)
AttributeCreator_3
    ATTR_TABLE = SET_TO fme_db_operation = DELETE
    -> Deleted (output)
