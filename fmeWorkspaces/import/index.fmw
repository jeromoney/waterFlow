FME workspace index.fmw

Creator
    GEOMTYPE = Geometry Object
    NUM = 1
    CREATED -> juicyriverImportData
juicyriverImportData

FME custom transformer UpdateDetector
This transformer is based on the ChangeDetector and extends its functionality by adding an Updated output port. It detects changes between two sets of input features.
One set of features enters the transformer via the Original port. The other set enters via the Revised port. Both sets must have a key attribute, which will be used to compare them against each other.
An Original feature is output via the Unchanged port when it is found to have matching key attribute and either matching geometry, matching attribute values, or both, with a feature in the Revised set.
An Original feature is output via the Deleted port when no key attribute match for it can be found in the Revised set.
A Revised feature with no key attribute match in the Original set is output via the Inserted port.
A Revised feature with key attribute match in the Original set and has changes either in geometry, or attribute values, or both, is output via the Updated port.
Inserted, updated and deleted features will have fme_db_operation set to INSERT, UPDATE or DELETE respectively.
Please note that to get correct results, the key attribute must be provided to both "Key Attribute" and "Attribute(s) to match" parameter prompts. 
Connect the transformer in your workspace and set the required parameters.
If Lenient Geometry Matching is set to yes then the order of points in line and area features will be ignored.
If Treat Blank Value as Different From Missing Attribute is Yes, then an attribute will be considered different for two features when one feature contains the attribute with a blank value and the other feature does not contain the attribute at all.
When geometry is being matched, Extra Vertex Tolerance can allow for extra vertices along line segments. A value of 0 means that no such extra vertices are permitted. A nonzero value controls how close any extra vertices must be to the line connecting the adjoining matching vertices. Note: This setting has no effect when using lenient geometry matching.

Parameters:
- KEYATTR =   # " " Key Attribute
- MATCH = 2D   # Match Geometry
- LENIENT_MATCH = no   # Lenient Geometry Matching
- MATCHATTRS =   # " " Attributes to Match
- BLANK_AND_MISSING_DIFFER = No   # Treat Blank Value as Different From Missing Attribute
- EXTRA_VERTEX_TOLERANCE = 0   # Extra Vertex Tolerance (optional)

Original (input)
    -> ATTRIBUTECREATOR
Note: Created by Dmitri Bagh / February 03, 2006 / dmitri.bagh@safe.com
Revised (input)
    -> ATTRIBUTECREATOR_2
Note: All parameters / are published / to match functionality / of ChangeDetector
Note: UPDATEDETECTOR
ChangeDetector
    BLANK_AND_MISSING_DIFFER = $(BLANK_AND_MISSING_DIFFER)
    EXTRA_VERTEX_TOLERANCE = $(EXTRA_VERTEX_TOLERANCE)
    LENIENT_MATCH = $(LENIENT_MATCH)
    MATCH = $(MATCH)
    MATCHATTRS = $(MATCHATTRS)
    MATCH_STRATEGY = Match Selected Attributes
    UNCHANGED -> ATTRIBUTEREMOVER_3
    ADDED -> Matcher_2
    DELETED -> Matcher
Updated (output)
Inserted (output)
Unchanged (output)
Deleted (output)

Bookmark: OrigFlag Creators
  Assigning OrigFlag Y for original 
  features and N for revised.
  For further use in testers 
  after Matcher 
  where original and revised 
  feaures can be merged together.
ATTRIBUTECREATOR: AttributeCreator
    ATTR_TABLE = SET_TO OrigFlag = Y
    -> ChangeDetector [ORIGINAL]
    -> Matcher_2
ATTRIBUTECREATOR_2: AttributeCreator
    ATTR_TABLE = SET_TO OrigFlag = N
    -> ChangeDetector [REVISED]
    -> Matcher

Bookmark: Matchers
  Here published Key Attribute
  distinguishes between added 
  and modified (above), 
  and - between deleted 
  and modified (below)
Matcher_2
    BLANK_AND_MISSING_DIFFER = No
    CNT_ATTR = _match_id
    DIFFATTRS = OrigFlag
    LENIENT_MATCH = No
    MATCH = NONE
    MATCHATTRS = $(KEYATTR)
    MATCH_STRATEGY = Match Selected Attributes
    MATCHED -> TESTER
    NOT_MATCHED -> TESTER_2
Matcher
    BLANK_AND_MISSING_DIFFER = No
    CNT_ATTR = _match_id
    DIFFATTRS = OrigFlag
    LENIENT_MATCH = No
    MATCH = NONE
    MATCHATTRS = $(KEYATTR)
    MATCH_STRATEGY = Match Selected Attributes
    NOT_MATCHED -> TESTER_3

Bookmark: Testers
  For updated and added 
  we keep revised features
  For deleted - original features
TESTER: Tester
    BOOL_OP = OR
    TEST_CLAUSE = TEST @Value(OrigFlag) = N
    PASSED -> ATTRIBUTEREMOVER
TESTER_2: Tester
    BOOL_OP = OR
    TEST_CLAUSE = TEST @Value(OrigFlag) = N
    PASSED -> ATTRIBUTEREMOVER_2
TESTER_3: Tester
    BOOL_OP = OR
    TEST_CLAUSE = TEST @Value(OrigFlag) = Y
    PASSED -> ATTRIBUTEREMOVER_4

Bookmark: Deleting temp attributes
ATTRIBUTEREMOVER: AttributeRemover
    REMOVE_ATTRS = _match_id,OrigFlag
    -> AttributeCreator
ATTRIBUTEREMOVER_2: AttributeRemover
    REMOVE_ATTRS = _match_id,OrigFlag
    -> AttributeCreator_2
ATTRIBUTEREMOVER_3: AttributeRemover
    REMOVE_ATTRS = OrigFlag
    -> Unchanged (output)
ATTRIBUTEREMOVER_4: AttributeRemover
    REMOVE_ATTRS = _match_id,OrigFlag
    -> AttributeCreator_3

Bookmark: Add fme_db_operation attribute
AttributeCreator
    ATTR_TABLE = SET_TO fme_db_operation = UPDATE
    -> Updated (output)
AttributeCreator_2
    ATTR_TABLE = SET_TO fme_db_operation = INSERT
    -> Inserted (output)
AttributeCreator_3
    ATTR_TABLE = SET_TO fme_db_operation = DELETE
    -> Deleted (output)

FME custom transformer canada

Parameters:
- province = BC

Input (input)
    -> FeatureReader [INITIATOR]
    -> FeatureReader_3 [INITIATOR]

Bookmark: Gauge reading
FeatureReader
    ATTRIBUTES = CSV,""" ID"",""Name / Nom"",Latitude,Longitude,Prov/Terr,""Timezone / Fuseau horaire"""
    ATTR_ACCUM_MODE = Only Use Result
    COMBINE_GEOM = Use Result
    CSV2_CASE_SENSITIVE_FIELD_NAMES = Yes
    CSV2_DATA_START_LINE = 2
    CSV2_DELIMITER = ,
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = http://dd.weather.gc.ca/hydrometric/doc/hydrometric_StationList.csv
    FORMAT = CSV2
    INTERACT = <No Spatial Filter>
    OUTPUT_FEATURES_DISPLAY = Schema and Data Features
    CSV -> BulkAttributeRenamer
BulkAttributeRenamer
    ATTRCHOICE = All Attributes
    CASE_CHANGE_TYPE = lower
    MODE_CHOICE = RENAME
    PATTERN_ACTION_DISP = CASECHANGE
    -> VertexCreator
VertexCreator
    MODE_NAME = Add Point
    XVAL = @Value(longitude)
    YVAL = @Value(latitude)
    -> AttributeManager
AttributeManager
    ATTR_TABLE:
      RENAME_SET_VALUE  id > id
      RENAME_SET_VALUE name / nom > name
      REMOVE latitude
      REMOVE longitude
      REMOVE prov/terr
      REMOVE timezone / fuseau horaire
      SET_TO datasource = CANADA
      SET_TO url = https://wateroffice.ec.gc.ca/report/real_time_e.html?stn=@Value(id)
    -> CoordinateSystemSetter
CoordinateSystemSetter
    COORDSYS = EPSG:4326
    -> FeatureJoiner [LEFT]
FeatureJoiner
    ATTR_CONFLICT_RES = Use Left
    GEOMETRY_HANDLING = Use Left
    JOIN_KEYS = id gauge AUTO
    JOIN_MODE = Inner
    JOINED -> gauge (output)
gauge (output)

Bookmark: Data Reading
FeatureReader_3
    ATTRIBUTES = public.candianprovinceabbrev,"abbreviation,english_name,french_name,source"
    ATTR_ACCUM_MODE = Only Use Result
    COMBINE_GEOM = Use Result
    DATASET = postgres
    FEATURETYPES = public.candianprovinceabbrev
    FORMAT = POSTGRES
    OUTPUT_FEATURES_DISPLAY = Schema and Data Features
    POSTGRES_FEATURES_PER_FETCH = 10000
    POSTGRES_NAMED_CONNECTION = postgres
    POSTGRES_QUERY_FEATURE_TYPES_FOR_MERGE_FILTERS = Yes
    POSTGRES_READ_TIME_WITH_TIMEZONE = Yes
    public.candianprovinceabbrev -> FeatureReader_4 [INITIATOR]
FeatureReader_4
    ATTRIBUTES = CSV,""" ID"",Date,""Water Level / Niveau d'eau (m)"",Grade,""Symbol / Symbole"",QA/QC,""Discharge / Débit (cms)"",Grade00,""Symbol / Symbole00"",QA/QC00"
    ATTR_ACCUM_MODE = Only Use Result
    COMBINE_GEOM = Use Result
    CSV2_CASE_SENSITIVE_FIELD_NAMES = Yes
    CSV2_DATA_START_LINE = 2
    CSV2_DELIMITER = ,
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = http://dd.weather.gc.ca/hydrometric/csv/@Value(abbreviation)/hourly/@Value(abbreviation)_hourly_hydrometric.csv
    FORMAT = CSV2
    INTERACT = <No Spatial Filter>
    OUTPUT_FEATURES_DISPLAY = Schema and Data Features
    CSV -> AttributeFilter
AttributeFilter
    ATTR_NAME = Discharge / Débit (cms)
    ATTR_VALUES = <Empty>,<Missing>,<Null>,<Unfiltered>
    <UNFILTERED> -> AttributeManager_2
AttributeManager_2
    ATTR_TABLE:
      RENAME_SET_VALUE  ID > gauge
      RENAME_SET_VALUE Date > measure_time
      REMOVE Water Level / Niveau d'eau (m)
      REMOVE Grade
      REMOVE Symbol / Symbole
      REMOVE QA/QC
      RENAME_SET_VALUE Discharge / Débit (cms) > value = @Evaluate(@round(@Value(value)*35.3147,0))
      REMOVE Grade00
      REMOVE Symbol / Symbole00
      REMOVE QA/QC00
    -> Sampler
Sampler
    GROUP_BY = gauge
    RATE = 1
    SAMPLE_MODE = No
    SAMPLE_TYPE_LONG = Last N Features
    SAMPLED -> FeatureJoiner [RIGHT]

FME custom transformer American Whitewater Reader

Input (input)
    -> FeatureReader_2 [INITIATOR]
AttributeKeeper
    KEEP_ATTRS = stusps
    -> AttributeManager_3
AttributeManager_3
    ATTR_TABLE = SET_TO url = http://www.americanwhitewater.org/content/River/state-summary/state/@Value(stusps)/.kml
    -> FeatureReader [INITIATOR]
FeatureReader
    ATTRIBUTES = AnimatedUpdate,,Document,,FlyTo,,Folder,,GroundOverlay,,NetworkLink,,PhotoOverlay,,Placemark,,ScreenOverlay,,SoundCue,,Style,,StyleMap,,Tour,,TourControl,,Wait,
    ATTR_ACCUM_MODE = Only Use Result
    COMBINE_GEOM = Use Result
    DATASET = @Value(url)
    FEATURETYPES = Placemark
    FORMAT = OGCKML
    INTERACT = <No Spatial Filter>
    OGCKML_KML21_APPLY_MODEL_TRANSFORMS = No
    OGCKML_KML21_DELETE_DOWNLOADED_FILES = Yes
    OGCKML_KML21_FAIL_ON_NETWORK_ERROR = No
    OGCKML_KML21_LOG_VERBOSE = No
    OGCKML_KML21_MAX_NETWORKLINK_TRAVERSAL_DEPTH = 5
    OGCKML_KML21_MOVE_TO_KML_WORLD_COORDSYS = Yes
    OGCKML_KML21_RASTER_READ_MODE = GroundOverlay
    OGCKML_KML21_SCAN_SCHEMA = Yes
    OGCKML_KML21_TRAVERSE_NETWORKLINKS = All
    OGCKML_USE_SEARCH_ENVELOPE = NO
    OUTPUT_FEATURES_DISPLAY = Schema and Data Features
    Placemark -> AttributeExposer
AttributeExposer
    ATTR_LIST = kml_name,kml_description,kml_style_url
    -> AttributeManager
AttributeManager
    ATTR_TABLE:
      RENAME_SET_VALUE kml_name > name
      RENAME_SET_VALUE kml_style_url > level
      RENAME_SET_VALUE kml_description > awid
    -> StringReplacer
StringReplacer
    CASE = NO
    FIND_TEXT = #style_
    NO_MATCH = _FME_NO_OP_
    REGEXP = NO
    SRC_ATTRS = level
    -> StringSearcher
StringSearcher
    CASE = no
    MATCHED_RESULT_ATTR = awid
    REGEXP = (?<=detail/id/)\d+
    STRING_TO_SEARCH = @Value(awid)
    MATCHED -> DuplicateFilter
DuplicateFilter
    INPUT_ORDERED_CHOICE = No
    KEYATTR = awid
    UNIQUE -> UpdateDetector [Revised]
    UNIQUE -> DateTimeStamper
DateTimeStamper
    DATETIME_ATTR = recorddate
    INCLUDE_OFFSET = NO
    STAMP_TYPE = datetime
    TIMEZONE = utc
    -> AttributeManager_2
AttributeManager_2
    ATTR_TABLE:
      REMOVE name
      SET_TO recorddate = @TimeZoneSet(@Value(recorddate),utc)
      SET_TO table = riverlevels_data
    -> NullAttributeMapper
NullAttributeMapper
    ATTRCHOICE = Selected Attributes
    ATTRLIST = level
    NULL_TREATMENT = Null
    SOURCE_ATTR_VAL = Null Empty
    -> UpdateDetector_2 [Revised]
UpdateDetector_2
    BLANK_AND_MISSING_DIFFER = No
    EXTRA_VERTEX_TOLERANCE = 0
    KEYATTR = awid
    LENIENT_MATCH = no
    MATCH = 2D
    MATCHATTRS = level awid recorddate
    Updated -> Junction_2
    Inserted -> Junction_2
    Deleted -> Junction_2
AttributeManager_4
    ATTR_TABLE = SET_TO table = riverlevels
    -> Junction_2
Junction_2
    -> AttributeExposer_2
AttributeExposer_2
    ATTR_LIST = fme_feature_type
    -> FeatureWriter [Output]
FeatureWriter
    DATASET = postgres
    DATASET_ATTR = _dataset
    FEATURE_TYPE_LIST_ATTR = _feature_type
    FORMAT = POSTGIS
    POSTGIS_BULK_COPY = YES
    POSTGIS_COORDINATE_SYSTEM_GRANULARITY = FEATURE_TYPE
    POSTGIS_GENERIC_GEOMETRY = yes
    POSTGIS_INSERT_TEXT_GEOMETRY = NO
    POSTGIS_LOWERCASE_ATTRIBUTE_NAMES = Yes
    POSTGIS_NAMED_CONNECTION = postgres
    POSTGIS_SPATIAL_COLUMN_NAME = geom
    POSTGIS_SPATIAL_COLUMN_TYPE = geometry
    POSTGIS_START_TRANSACTION = 0
    POSTGIS_STRICT_TEMPORAL_TYPE_HANDLING = Yes
    POSTGIS_TRANSACTION_INTERVAL = 1000
    TOTAL_FEATURES_WRITTEN_ATTR = _total_features_written

Bookmark: Read Postgis data to check for updates
FeatureReader_2
    ATTRIBUTES = public.cb_2017_us_state_500k,"ogc_fid,statefp,statens,affgeoid,geoid,stusps,name,lsad,aland,awater",public.riverlevels,"name,awid,hydroseq,difficulty,difficulty_numeric,state",public.riverlevels_data,"awid,level,recorddate"
    ATTR_ACCUM_MODE = Merge Initiator and Result
    ATTR_CONFLICT_RES = Use Result
    COMBINE_GEOM = Use Result
    DATASET = postgres
    FEATURETYPES = public.cb_2017_us_state_500k public.riverlevels public.riverlevels_data
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = postgres
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    public.cb_2017_us_state_500k -> AttributeKeeper
    public.riverlevels -> UpdateDetector [Original]
    public.riverlevels_data -> UpdateDetector_2 [Original]

Bookmark: Looking for new sections
UpdateDetector
    BLANK_AND_MISSING_DIFFER = No
    EXTRA_VERTEX_TOLERANCE = 0
    KEYATTR = awid
    LENIENT_MATCH = no
    MATCH = 2D
    MATCHATTRS = awid name
    Updated -> AttributeManager_4
    Inserted -> AttributeManager_4
    Deleted -> AttributeManager_4

FME custom transformer USGS Reader

FeatureJoiner
    ATTR_CONFLICT_RES = Use Right
    GEOMETRY_HANDLING = Use Left
    JOIN_KEYS = gml_parent_id gml_parent_id AUTO
    JOIN_MODE = Inner
    JOINED -> AttributeManager_3

Bookmark: data query
Input (input)
    -> FeatureReader_2 [INITIATOR]
FeatureReader_2
    ATTRIBUTES = public.usgs_count,_count
    ATTR_ACCUM_MODE = Only Use Result
    COMBINE_GEOM = Use Result
    DATASET = postgres
    FEATURETYPES = public.usgs_count
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = postgres
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    public.usgs_count -> StringPadder
StringPadder
    BLANK_ATTRIBUTE = Yes
    PADCHAR = 0
    SIDE = Left
    SRC_ATTRS = _count
    WIDTH = 2
    -> AttributeManager_7
AttributeManager_7
    ATTR_TABLE = SET_TO url = https://waterservices.usgs.gov/nwis/iv/?format=waterml,2.0&parameterCd=00060&siteType=ST&period=PT1H&siteStatus=all&huc=@Value(_count)
    -> FeatureReader [INITIATOR]
FeatureReader
    ATTRIBUTES =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
    ATTR_ACCUM_MODE = Only Use Result
    COMBINE_GEOM = Use Result
    DATASET = @Value(url)
    FEATURETYPES = MeasurementTimeseries MonitoringPoint
    FORMAT = GML
    GML_ADD_GEOMETRIES_AS_XML_FRAGMENTS = NO
    GML_CACHE_XSD = yes
    GML_CONTINUE_ON_GEOM_ERROR = yes
    GML_DISABLE_AUTOMATIC_READER_TYPE_SELECTION = NO
    GML_DISABLE_XML_NAMESPACE_PROCESSING = NO
    GML_ENFORCE_PATH_CONTINUITY_BY = SNAPPING_END_POINTS
    GML_EXPLORE_XSD_VALUES = NO
    GML_FEATURE_TYPES_SCHEMA_MODE = XML_SCHEMA
    GML_FLATTEN_XML_FRAGMENTS = NO
    GML_IGNORE_APPLICATON_SCHEMA = no
    GML_MAP_ALL_SUBSTITUTABLE_PROPERTIES = YES
    GML_MAP_COMPLEX_PROPERTIES_AS = Nested Attributes
    GML_MAP_EMBEDDED_OBJECTS_AS = ATTRIBUTES
    GML_MAP_GEOMETRY_COLUMNS = YES
    GML_MAP_PREDEFINED_GML_PROPERTIES = NO
    GML_MULTI_VALUE_SIMPLE_PROPERTIES_AS_CSV = no
    GML_SKIP_SCHEMA_LOCATION_IN_DATASET = No
    GML_USE_OLD_READER = NO
    GML_USE_SEARCH_ENVELOPE = NO
    GML_VALIDATE_DATASET = no
    GML_XML_FRAGMENTS_AS_DOCUMENTS = YES
    INTERACT = <No Spatial Filter>
    OUTPUT_FEATURES_DISPLAY = Schema and Data Features
    MeasurementTimeseries -> AttributeKeeper
    MonitoringPoint -> AttributeKeeper_2

Bookmark: data preprocessing
AttributeKeeper
    KEEP_ATTRS = gml_parent_id,gml_id,gml_parent_property
    KEEP_LIST = point{}.MeasurementTVP.time point{}.MeasurementTVP.value
    -> ListExploder
ListExploder
    ATTR_ACCUM_MODE = Merge List Attributes
    ATTR_CONFLICT_RES = Use List Attribute Values
    INDEX_ATTR = _element_index
    LIST_ATTR = point{}
    ELEMENTS -> Sampler
Sampler
    GROUP_BY = gml_parent_id
    RATE = 1
    SAMPLE_MODE = No
    SAMPLE_TYPE_LONG = Last N Features
    SAMPLED -> SubstringExtractor_2
SubstringExtractor_2
    END = 15
    RESULT_ATTR = stationID
    SRC_STRING = @Value(gml_id)
    START = 8
    -> AttributeManager_2
AttributeManager_2
    ATTR_TABLE:
      RENAME_SET_VALUE MeasurementTVP.time > time
      RENAME_SET_VALUE MeasurementTVP.value > flow
      REMOVE gml_parent_property
      REMOVE gml_id
      REMOVE _element_index
      REMOVE stationID
      REMOVE MeasurementTVP.time.frame
      REMOVE MeasurementTVP.time.calendarEraName
      REMOVE MeasurementTVP.time.indeterminatePosition
      REMOVE MeasurementTVP.value.uom
      REMOVE MeasurementTVP.value.xsi_nil
    -> FeatureJoiner [RIGHT]

Bookmark: gauge preprocessing
AttributeKeeper_2
    KEEP_ATTRS = gml_parent_id,gml_id,sampledFeature.xlink_title,gml_parent_property
    -> AttributeManager
AttributeManager
    ATTR_TABLE:
      RENAME_SET_VALUE sampledFeature.xlink_title > gnisname
      REMOVE gml_parent_property
      REMOVE gml_id
      SET_TO gauge_id = @Value(gml_parent_id)
    -> SubstringExtractor
SubstringExtractor
    END = 16
    RESULT_ATTR = gauge_id
    SRC_STRING = @Value(gauge_id)
    START = 9
    -> FeatureJoiner [LEFT]

Bookmark: gauges
AttributeManager_3
    ATTR_TABLE:
      RENAME_SET_VALUE flow > value
      SET_TO id = @Value(gauge_id)_@Value(gnisname)
      SET_TO datasource = USGS
      SET_TO url = https://waterdata.usgs.gov/nwis/uv?@Value(gauge_id)
      REMOVE gml_parent_id
    -> AttributeManager_4
Note: Attached a second attribute manager to seperate renaming variable and formulas
AttributeManager_4
    ATTR_TABLE:
      RENAME_SET_VALUE time > measure_time
      REMOVE gauge_id
      RENAME_SET_VALUE gnisname > name
      SET_TO datasource = USGS
      SET_TO watershed = 01
    -> DuplicateFilter
DuplicateFilter
    INPUT_ORDERED_CHOICE = No
    KEYATTR = datasource name url watershed id
    UNIQUE -> gauge (output)
gauge (output)

FME custom transformer coloradoDWR

Input (input)
    -> FeatureReader [INITIATOR]
FeatureReader
    ATTRIBUTES = GeoJsonFeatureCollection,"division,waterDistrict,county,stationName,dataSourceAbbrev,dataSource,waterSource,gnisId,streamMile,abbrev,usgsStationId,stationStatus,stationType,structureType,measDateTime,parameter,stage,measValue,units,flagA,flagB,contrArea,drainArea,huc10,utmX,utmY,latitude,longitude,locationAccuracy,wdid,modified,moreInformation,fme_geometry{0}"
    ATTR_ACCUM_MODE = Only Use Result
    COMBINE_GEOM = Use Result
    DATASET = http://dnrweb.state.co.us/DWR/DwrApiService/api/v2/telemetrystations/telemetrystation/?format=geo&stationType=Stream+Gage
    FEATURETYPES = GeoJsonFeatureCollection
    FORMAT = GEOJSON
    GEOJSON_FLATTEN_MODE = ALL_LEVELS
    GEOJSON_USE_BASENAME_AS_DEFAULT_FEATURE_TYPE = Yes
    GEOJSON_USE_SEARCH_ENVELOPE = NO
    INTERACT = <No Spatial Filter>
    OUTPUT_FEATURES_DISPLAY = Schema and Data Features
    GeoJsonFeatureCollection -> Tester
Note: Retrieves latest data from Colorado DWR sources. / http://dnrweb.state.co.us/DWR/DwrApiService/api/v2/telemetrystations/telemetrystation/?format=geo&stationType=Stream+Gage
Tester
    BOOL_OP = AND
    TEST_CLAUSE:
      TEST @Value(dataSourceAbbrev) != USGS
      TEST @Value(parameter) = DISCHRG
      TEST @Value(stationStatus) = Active
      TEST @Value(measValue) > 0
    PASSED -> AttributeManager
AttributeManager
    ATTR_TABLE:
      REMOVE division
      REMOVE waterDistrict
      REMOVE county
      RENAME_SET_VALUE stationName > name
      RENAME_SET_VALUE dataSourceAbbrev > datasource
      REMOVE dataSource
      RENAME_SET_VALUE waterSource > watersourcename
      REMOVE streamMile
      REMOVE abbrev
      SET_TO usgsStationId > id = FME_CONDITIONAL:DEFAULT_VALUE'@Value(gnisId)_@Value(name)'BOOL_OP;AND;COMPOSITE_TEST;<Unused>;TEST @Value(usgsStationId) != null;TEST @Value(usgsStationId) TYPE INT'@Value(usgsStationId)_@Value(name)
        'FME_NUM_CONDITIONS2___
      REMOVE stationStatus
      REMOVE stationType
      REMOVE structureType
      RENAME_SET_VALUE measDateTime > measure_time
      REMOVE parameter
      REMOVE stage
      RENAME_SET_VALUE measValue > value
      REMOVE units
      REMOVE flagA
      REMOVE flagB
      REMOVE contrArea
      REMOVE drainArea
      REMOVE huc10
      REMOVE utmX
      REMOVE utmY
      REMOVE latitude
      REMOVE longitude
      REMOVE locationAccuracy
      REMOVE wdid
      REMOVE modified
      RENAME_SET_VALUE moreInformation > url
    -> AttributeManager_2
AttributeManager_2
    ATTR_TABLE = RENAME_SET_VALUE id > gauge
    -> Reprojector
Reprojector
    DEST = EPSG:4326
    INTERPOLATION_TYPE_NAME = Nearest Neighbor
    RASTER_CELL_SIZE = Preserve Cells
    RASTER_TOLERANCE = 0.0
    SOURCE = Read from feature
    REPROJECTED -> AttributeManager_3
AttributeManager_3
    ATTR_TABLE:
      SET_TO datasource = DWR
      RENAME_SET_VALUE gauge > id
      REMOVE usgsStationId
      REMOVE gnisId
      REMOVE fme_geometry{0}
      REMOVE fme_geometry{}
    -> gauge (output)
gauge (output)

FME custom transformer juicyriverImportData

Input (input)
    -> USGS_Reader [off]
    -> American_Whitewater_Reader [off]
    -> NOAA
    -> coloradoDWR [off]
    -> canada [off]
    -> FeatureReader_2 [INITIATOR]
American_Whitewater_Reader: American Whitewater Reader
DuplicateFilter
    INPUT_ORDERED_CHOICE = No
    KEYATTR = id
    UNIQUE -> UpdateDetector [Revised]
Output (output)

Bookmark: gauge writer
FeatureReader_2
    ATTRIBUTES = public.gauge,"watersource,datasource,name,url,watersourcename,id,watershed"
    ATTR_ACCUM_MODE = Only Use Result
    COMBINE_GEOM = Use Result
    DATASET = postgres
    FEATURETYPES = public.gauge
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = postgres
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    public.gauge -> UpdateDetector [Original]
UpdateDetector
    BLANK_AND_MISSING_DIFFER = No
    EXTRA_VERTEX_TOLERANCE = 0
    KEYATTR = id
    LENIENT_MATCH = no
    MATCH = 2D
    MATCHATTRS = value url watersourcename measure_time name
    Updated -> FeatureWriter [Output]
    Inserted -> FeatureWriter [Output]
FeatureWriter
    DATASET = postgres
    DATASET_ATTR = _dataset
    FEATURE_TYPE_LIST_ATTR = _feature_type
    FORMAT = POSTGIS
    POSTGIS_BULK_COPY = YES
    POSTGIS_COORDINATE_SYSTEM_GRANULARITY = FEATURE_TYPE
    POSTGIS_GENERIC_GEOMETRY = yes
    POSTGIS_INSERT_TEXT_GEOMETRY = NO
    POSTGIS_LOWERCASE_ATTRIBUTE_NAMES = Yes
    POSTGIS_NAMED_CONNECTION = postgres
    POSTGIS_SPATIAL_COLUMN_NAME = geom
    POSTGIS_SPATIAL_COLUMN_TYPE = geometry
    POSTGIS_START_TRANSACTION = 0
    POSTGIS_STRICT_TEMPORAL_TYPE_HANDLING = Yes
    POSTGIS_TRANSACTION_INTERVAL = 1000
    TOTAL_FEATURES_WRITTEN_ATTR = _total_features_written
    SUMMARY -> Output (output)

Bookmark: Gauge Readers
USGS_Reader: USGS Reader
    gauge -> DuplicateFilter
canada
    province = BC
    gauge -> DuplicateFilter
coloradoDWR
    gauge -> DuplicateFilter
NOAA
    gauge -> DuplicateFilter

FME custom transformer NOAA

Input (input)
    -> SystemCaller
SystemCaller
    ATTR = success
    CMD = wget https://water.weather.gov/ahps/download.php?data=tgz_obs -O /tmp/noaa.tgz && mkdir -p /tmp/noaa && tar -xvzf /tmp/noaa.tgz -C /tmp/noaa
    -> FeatureReader [INITIATOR]
FeatureReader
    ATTRIBUTES = national_shapefile_obs,"GaugeLID,Status,Location,Latitude,Longitude,Waterbody,State,Observed,ObsTime,Units,Action,Flood,Moderate,Major,LowThresh,LowThreshU,WFO,HDatum,PEDTS,SecValue,SecUnit,URL"
    ATTR_ACCUM_MODE = Only Use Result
    COMBINE_GEOM = Use Result
    DATASET = /tmp/noaa/national_shapefile_obs.shp
    ESRISHAPE_CHECK_NUMERIC_FIELDS = yes
    ESRISHAPE_DISSOLVE_HOLES = no
    ESRISHAPE_MEASURES_AS_Z = no
    ESRISHAPE_NUMERIC_TYPE_ATTRIBUTE_HANDLING = STANDARD_TYPES
    ESRISHAPE_REPORT_BAD_GEOMETRY = no
    ESRISHAPE_SIMPLE_DONUT_GEOMETRY = simple
    ESRISHAPE_TRIM_PRECEDING_SPACES = yes
    ESRISHAPE_UPPER_CASE_ATTR_NAMES = No
    ESRISHAPE_USE_SEARCH_ENVELOPE = NO
    FEATURETYPES = national_shapefile_obs
    FORMAT = ESRISHAPE
    INTERACT = <No Spatial Filter>
    OUTPUT_FEATURES_DISPLAY = Schema and Data Features
    national_shapefile_obs -> Tester
Note: https://water.weather.gov/ahps/download.php?data=tgz_obs
Tester
    BOOL_OP = AND
    TEST_CLAUSE:
      TEST @Value(Status) != obs_not_current
      TEST @Value(Status) != out_of_service
    PASSED -> AttributeManager
AttributeManager
    ATTR_TABLE:
      RENAME_SET_VALUE GaugeLID > id
      REMOVE Status
      RENAME_SET_VALUE Location > name
      REMOVE Latitude
      REMOVE Longitude
      RENAME_SET_VALUE Waterbody > watersourcename
      REMOVE State
      REMOVE Observed
      RENAME_SET_VALUE ObsTime > measure_time = @Value(measure_time)
      REMOVE Units
      REMOVE Action
      REMOVE Flood
      REMOVE Moderate
      REMOVE Major
      REMOVE LowThresh
      REMOVE LowThreshU
      REMOVE WFO
      REMOVE HDatum
      REMOVE PEDTS
      RENAME_SET_VALUE SecValue > value
      REMOVE SecUnit
      RENAME_SET_VALUE URL > url
      SET_TO datasource = NOAA
    -> AttributeRangeFilter
AttributeRangeFilter
    IN_ATTR = value
    LUT = 0.01,,positive
    positive -> AttributeManager_2
gauge (output)

Bookmark: Lakes are not multiplied by 1000
AttributeManager_2
    ATTR_TABLE:
      REMOVE watersourcename
      SET_TO value = FME_CONDITIONAL:DEFAULT_VALUE'@int(@mult(@Value(value),1000))'BOOL_OP;OR;COMPOSITE_TEST;<Unused>;CASE_INSENSITIVE_TEST @Value(name) BEGINS_WITH Lake'@int(@Value(value))'FME_NUM_CONDITIONS2___
      REMOVE url
      SET_TO datasource = NOAA
    -> gauge (output)
