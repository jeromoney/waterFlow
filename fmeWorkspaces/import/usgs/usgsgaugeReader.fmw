FME workspace usgsgaugeReader.fmw

Parameters:
- watershed = 01   # Watershed number
- SourceDataset_POSTGIS_2 = postgres   # Connection
- DestDataset_POSTGIS = postgres   # Connection
- SourceDataset_POSTGRES = postgres   # Connection
- DestDataset_POSTGRES = postgres   # Connection

Readers:
- GML_1: GML from https://waterservices.usgs.gov/nwis/iv/?format=waterml,2.0&parameterCd=00060&siteType=ST&period=PT1H&siteStatus=all&huc=$(watershed)
- POSTGIS_1: POSTGIS from $(SourceDataset_POSTGIS_2)
- POSTGRES_1: POSTGRES from $(SourceDataset_POSTGRES)

Writers:
- POSTGIS_2: POSTGIS to $(DestDataset_POSTGIS)
- POSTGRES_2: POSTGRES to $(DestDataset_POSTGRES)

MeasurementTimeseries (reader GML_1)
    attributes: metadata.owns xml_boolean, metadata.MeasurementTimeseriesMetadata.temporalExtent.nilReason xml_buffer, metadata.MeasurementTimeseriesMetadata.temporalExtent.gml_remoteSchema xml_buffer, metadata.MeasurementTimeseriesMetadata.temporalExtent.xlink_href xml_buffer, metadata.MeasurementTimeseriesMetadata.temporalExtent.xlink_title xml_buffer, metadata.MeasurementTimeseriesMetadata.temporalExtent.owns xml_boolean, metadata.MeasurementTimeseriesMetadata.temporalExtent.gml_TimePeriod.frame xml_buffer, metadata.MeasurementTimeseriesMetadata.temporalExtent.gml_TimePeriod.gml_id xml_buffer, metadata.MeasurementTimeseriesMetadata.temporalExtent.gml_TimePeriod.gml_relatedTime{} xml_xml, metadata.MeasurementTimeseriesMetadata.temporalExtent.gml_TimePeriod.gml_beginPosition xml_buffer, metadata.MeasurementTimeseriesMetadata.temporalExtent.gml_TimePeriod.gml_beginPosition.frame xml_buffer, metadata.MeasurementTimeseriesMetadata.temporalExtent.gml_TimePeriod.gml_beginPosition.calendarEraName xml_buffer, metadata.MeasurementTimeseriesMetadata.temporalExtent.gml_TimePeriod.gml_beginPosition.indeterminatePosition xml_char(7), metadata.MeasurementTimeseriesMetadata.temporalExtent.gml_TimePeriod.gml_begin.nilReason xml_buffer, metadata.MeasurementTimeseriesMetadata.temporalExtent.gml_TimePeriod.gml_begin.gml_remoteSchema xml_buffer, metadata.MeasurementTimeseriesMetadata.temporalExtent.gml_TimePeriod.gml_begin.xlink_href xml_buffer, metadata.MeasurementTimeseriesMetadata.temporalExtent.gml_TimePeriod.gml_begin.xlink_title xml_buffer, metadata.MeasurementTimeseriesMetadata.temporalExtent.gml_TimePeriod.gml_begin.owns xml_boolean, metadata.MeasurementTimeseriesMetadata.temporalExtent.gml_TimePeriod.gml_begin.gml_TimeInstant.frame xml_buffer, metadata.MeasurementTimeseriesMetadata.temporalExtent.gml_TimePeriod.gml_begin.gml_TimeInstant.gml_id xml_buffer, metadata.MeasurementTimeseriesMetadata.temporalExtent.gml_TimePeriod.gml_begin.gml_TimeInstant.gml_relatedTime{} xml_xml, metadata.MeasurementTimeseriesMetadata.temporalExtent.gml_TimePeriod.gml_begin.gml_TimeInstant.gml_timePosition xml_buffer, metadata.MeasurementTimeseriesMetadata.temporalExtent.gml_TimePeriod.gml_begin.gml_TimeInstant.gml_timePosition.frame xml_buffer, metadata.MeasurementTimeseriesMetadata.temporalExtent.gml_TimePeriod.gml_begin.gml_TimeInstant.gml_timePosition.calendarEraName xml_buffer, metadata.MeasurementTimeseriesMetadata.temporalExtent.gml_TimePeriod.gml_begin.gml_TimeInstant.gml_timePosition.indeterminatePosition xml_char(7), metadata.MeasurementTimeseriesMetadata.temporalExtent.gml_TimePeriod.gml_endPosition xml_buffer, metadata.MeasurementTimeseriesMetadata.temporalExtent.gml_TimePeriod.gml_endPosition.frame xml_buffer, metadata.MeasurementTimeseriesMetadata.temporalExtent.gml_TimePeriod.gml_endPosition.calendarEraName xml_buffer, metadata.MeasurementTimeseriesMetadata.temporalExtent.gml_TimePeriod.gml_endPosition.indeterminatePosition xml_char(7), metadata.MeasurementTimeseriesMetadata.temporalExtent.gml_TimePeriod.gml_end.nilReason xml_buffer,
      metadata.MeasurementTimeseriesMetadata.temporalExtent.gml_TimePeriod.gml_end.gml_remoteSchema xml_buffer, metadata.MeasurementTimeseriesMetadata.temporalExtent.gml_TimePeriod.gml_end.xlink_href xml_buffer, metadata.MeasurementTimeseriesMetadata.temporalExtent.gml_TimePeriod.gml_end.xlink_title xml_buffer, metadata.MeasurementTimeseriesMetadata.temporalExtent.gml_TimePeriod.gml_end.owns xml_boolean, metadata.MeasurementTimeseriesMetadata.temporalExtent.gml_TimePeriod.gml_end.gml_TimeInstant.frame xml_buffer, metadata.MeasurementTimeseriesMetadata.temporalExtent.gml_TimePeriod.gml_end.gml_TimeInstant.gml_id xml_buffer, metadata.MeasurementTimeseriesMetadata.temporalExtent.gml_TimePeriod.gml_end.gml_TimeInstant.gml_relatedTime{} xml_xml, metadata.MeasurementTimeseriesMetadata.temporalExtent.gml_TimePeriod.gml_end.gml_TimeInstant.gml_timePosition xml_buffer, metadata.MeasurementTimeseriesMetadata.temporalExtent.gml_TimePeriod.gml_end.gml_TimeInstant.gml_timePosition.frame xml_buffer, metadata.MeasurementTimeseriesMetadata.temporalExtent.gml_TimePeriod.gml_end.gml_TimeInstant.gml_timePosition.calendarEraName xml_buffer, metadata.MeasurementTimeseriesMetadata.temporalExtent.gml_TimePeriod.gml_end.gml_TimeInstant.gml_timePosition.indeterminatePosition xml_char(7), metadata.MeasurementTimeseriesMetadata.temporalExtent.gml_TimePeriod.gml_duration xml_buffer, metadata.MeasurementTimeseriesMetadata.temporalExtent.gml_TimePeriod.gml_timeInterval xml_real64, metadata.MeasurementTimeseriesMetadata.temporalExtent.gml_TimePeriod.gml_timeInterval.unit xml_buffer, metadata.MeasurementTimeseriesMetadata.temporalExtent.gml_TimePeriod.gml_timeInterval.radix xml_uint64, metadata.MeasurementTimeseriesMetadata.temporalExtent.gml_TimePeriod.gml_timeInterval.factor xml_int64, metadata.MeasurementTimeseriesMetadata.baseTime xml_buffer, metadata.MeasurementTimeseriesMetadata.baseTime.frame xml_buffer, metadata.MeasurementTimeseriesMetadata.baseTime.calendarEraName xml_buffer, metadata.MeasurementTimeseriesMetadata.baseTime.indeterminatePosition xml_char(7), metadata.MeasurementTimeseriesMetadata.spacing xml_buffer, metadata.MeasurementTimeseriesMetadata.commentBlock{}.owns xml_boolean, metadata.MeasurementTimeseriesMetadata.commentBlock{}.CommentBlock.applicablePeriod.nilReason xml_buffer, metadata.MeasurementTimeseriesMetadata.commentBlock{}.CommentBlock.applicablePeriod.gml_remoteSchema xml_buffer, metadata.MeasurementTimeseriesMetadata.commentBlock{}.CommentBlock.applicablePeriod.xlink_href xml_buffer, metadata.MeasurementTimeseriesMetadata.commentBlock{}.CommentBlock.applicablePeriod.xlink_title xml_buffer, metadata.MeasurementTimeseriesMetadata.commentBlock{}.CommentBlock.applicablePeriod.owns xml_boolean, metadata.MeasurementTimeseriesMetadata.commentBlock{}.CommentBlock.applicablePeriod.gml_TimePeriod.frame xml_buffer, metadata.MeasurementTimeseriesMetadata.commentBlock{}.CommentBlock.applicablePeriod.gml_TimePeriod.gml_id xml_buffer, metadata.MeasurementTimeseriesMetadata.commentBlock{}.CommentBlock.applicablePeriod.gml_TimePeriod.gml_relatedTime{} xml_xml,
      metadata.MeasurementTimeseriesMetadata.commentBlock{}.CommentBlock.applicablePeriod.gml_TimePeriod.gml_beginPosition xml_buffer, metadata.MeasurementTimeseriesMetadata.commentBlock{}.CommentBlock.applicablePeriod.gml_TimePeriod.gml_beginPosition.frame xml_buffer, metadata.MeasurementTimeseriesMetadata.commentBlock{}.CommentBlock.applicablePeriod.gml_TimePeriod.gml_beginPosition.calendarEraName xml_buffer, metadata.MeasurementTimeseriesMetadata.commentBlock{}.CommentBlock.applicablePeriod.gml_TimePeriod.gml_beginPosition.indeterminatePosition xml_char(7), metadata.MeasurementTimeseriesMetadata.commentBlock{}.CommentBlock.applicablePeriod.gml_TimePeriod.gml_begin.nilReason xml_buffer, metadata.MeasurementTimeseriesMetadata.commentBlock{}.CommentBlock.applicablePeriod.gml_TimePeriod.gml_begin.gml_remoteSchema xml_buffer, metadata.MeasurementTimeseriesMetadata.commentBlock{}.CommentBlock.applicablePeriod.gml_TimePeriod.gml_begin.xlink_href xml_buffer, metadata.MeasurementTimeseriesMetadata.commentBlock{}.CommentBlock.applicablePeriod.gml_TimePeriod.gml_begin.xlink_title xml_buffer, metadata.MeasurementTimeseriesMetadata.commentBlock{}.CommentBlock.applicablePeriod.gml_TimePeriod.gml_begin.owns xml_boolean, metadata.MeasurementTimeseriesMetadata.commentBlock{}.CommentBlock.applicablePeriod.gml_TimePeriod.gml_begin.gml_TimeInstant.frame xml_buffer, metadata.MeasurementTimeseriesMetadata.commentBlock{}.CommentBlock.applicablePeriod.gml_TimePeriod.gml_begin.gml_TimeInstant.gml_id xml_buffer, metadata.MeasurementTimeseriesMetadata.commentBlock{}.CommentBlock.applicablePeriod.gml_TimePeriod.gml_begin.gml_TimeInstant.gml_relatedTime{} xml_xml, metadata.MeasurementTimeseriesMetadata.commentBlock{}.CommentBlock.applicablePeriod.gml_TimePeriod.gml_begin.gml_TimeInstant.gml_timePosition xml_buffer, metadata.MeasurementTimeseriesMetadata.commentBlock{}.CommentBlock.applicablePeriod.gml_TimePeriod.gml_begin.gml_TimeInstant.gml_timePosition.frame xml_buffer, metadata.MeasurementTimeseriesMetadata.commentBlock{}.CommentBlock.applicablePeriod.gml_TimePeriod.gml_begin.gml_TimeInstant.gml_timePosition.calendarEraName xml_buffer, metadata.MeasurementTimeseriesMetadata.commentBlock{}.CommentBlock.applicablePeriod.gml_TimePeriod.gml_begin.gml_TimeInstant.gml_timePosition.indeterminatePosition xml_char(7), metadata.MeasurementTimeseriesMetadata.commentBlock{}.CommentBlock.applicablePeriod.gml_TimePeriod.gml_endPosition xml_buffer, metadata.MeasurementTimeseriesMetadata.commentBlock{}.CommentBlock.applicablePeriod.gml_TimePeriod.gml_endPosition.frame xml_buffer, metadata.MeasurementTimeseriesMetadata.commentBlock{}.CommentBlock.applicablePeriod.gml_TimePeriod.gml_endPosition.calendarEraName xml_buffer, metadata.MeasurementTimeseriesMetadata.commentBlock{}.CommentBlock.applicablePeriod.gml_TimePeriod.gml_endPosition.indeterminatePosition xml_char(7), metadata.MeasurementTimeseriesMetadata.commentBlock{}.CommentBlock.applicablePeriod.gml_TimePeriod.gml_end.nilReason xml_buffer, metadata.MeasurementTimeseriesMetadata.commentBlock{}.CommentBlock.applicablePeriod.gml_TimePeriod.gml_end.gml_remoteSchema xml_buffer, metadata.MeasurementTimeseriesMetadata.commentBlock{}.CommentBlock.applicablePeriod.gml_TimePeriod.gml_end.xlink_href xml_buffer, metadata.MeasurementTimeseriesMetadata.commentBlock{}.CommentBlock.applicablePeriod.gml_TimePeriod.gml_end.xlink_title xml_buffer, metadata.MeasurementTimeseriesMetadata.commentBlock{}.CommentBlock.applicablePeriod.gml_TimePeriod.gml_end.owns xml_boolean, metadata.MeasurementTimeseriesMetadata.commentBlock{}.CommentBlock.applicablePeriod.gml_TimePeriod.gml_end.gml_TimeInstant.frame xml_buffer, metadata.MeasurementTimeseriesMetadata.commentBlock{}.CommentBlock.applicablePeriod.gml_TimePeriod.gml_end.gml_TimeInstant.gml_id xml_buffer, metadata.MeasurementTimeseriesMetadata.commentBlock{}.CommentBlock.applicablePeriod.gml_TimePeriod.gml_end.gml_TimeInstant.gml_relatedTime{} xml_xml, metadata.MeasurementTimeseriesMetadata.commentBlock{}.CommentBlock.applicablePeriod.gml_TimePeriod.gml_end.gml_TimeInstant.gml_timePosition xml_buffer, metadata.MeasurementTimeseriesMetadata.commentBlock{}.CommentBlock.applicablePeriod.gml_TimePeriod.gml_end.gml_TimeInstant.gml_timePosition.frame xml_buffer,
      metadata.MeasurementTimeseriesMetadata.commentBlock{}.CommentBlock.applicablePeriod.gml_TimePeriod.gml_end.gml_TimeInstant.gml_timePosition.calendarEraName xml_buffer, metadata.MeasurementTimeseriesMetadata.commentBlock{}.CommentBlock.applicablePeriod.gml_TimePeriod.gml_end.gml_TimeInstant.gml_timePosition.indeterminatePosition xml_char(7), metadata.MeasurementTimeseriesMetadata.commentBlock{}.CommentBlock.applicablePeriod.gml_TimePeriod.gml_duration xml_buffer, metadata.MeasurementTimeseriesMetadata.commentBlock{}.CommentBlock.applicablePeriod.gml_TimePeriod.gml_timeInterval xml_real64, metadata.MeasurementTimeseriesMetadata.commentBlock{}.CommentBlock.applicablePeriod.gml_TimePeriod.gml_timeInterval.unit xml_buffer, metadata.MeasurementTimeseriesMetadata.commentBlock{}.CommentBlock.applicablePeriod.gml_TimePeriod.gml_timeInterval.radix xml_uint64, metadata.MeasurementTimeseriesMetadata.commentBlock{}.CommentBlock.applicablePeriod.gml_TimePeriod.gml_timeInterval.factor xml_int64, metadata.MeasurementTimeseriesMetadata.commentBlock{}.CommentBlock.comment xml_buffer, metadata.MeasurementTimeseriesMetadata.parameter{}.nilReason xml_buffer, metadata.MeasurementTimeseriesMetadata.parameter{}.gml_remoteSchema xml_buffer, metadata.MeasurementTimeseriesMetadata.parameter{}.xlink_href xml_buffer, metadata.MeasurementTimeseriesMetadata.parameter{}.xlink_title xml_buffer, metadata.MeasurementTimeseriesMetadata.parameter{}.NamedValue.name.owns xml_boolean, metadata.MeasurementTimeseriesMetadata.parameter{}.NamedValue.name.nilReason xml_buffer, metadata.MeasurementTimeseriesMetadata.parameter{}.NamedValue.name.gml_remoteSchema xml_buffer, metadata.MeasurementTimeseriesMetadata.parameter{}.NamedValue.name.xlink_href xml_buffer, metadata.MeasurementTimeseriesMetadata.parameter{}.NamedValue.name.xlink_title xml_buffer, metadata.MeasurementTimeseriesMetadata.parameter{}.NamedValue.value xml_xml, metadata.MeasurementTimeseriesMetadata.startAnchorPoint xml_buffer, metadata.MeasurementTimeseriesMetadata.startAnchorPoint.frame xml_buffer, metadata.MeasurementTimeseriesMetadata.startAnchorPoint.calendarEraName xml_buffer, metadata.MeasurementTimeseriesMetadata.startAnchorPoint.indeterminatePosition xml_char(7), metadata.MeasurementTimeseriesMetadata.endAnchorPoint xml_buffer, metadata.MeasurementTimeseriesMetadata.endAnchorPoint.frame xml_buffer, metadata.MeasurementTimeseriesMetadata.endAnchorPoint.calendarEraName xml_buffer, metadata.MeasurementTimeseriesMetadata.endAnchorPoint.indeterminatePosition xml_char(7), metadata.MeasurementTimeseriesMetadata.cumulative xml_boolean, metadata.MeasurementTimeseriesMetadata.accumulationAnchorTime xml_buffer, metadata.MeasurementTimeseriesMetadata.accumulationAnchorTime.frame xml_buffer, metadata.MeasurementTimeseriesMetadata.accumulationAnchorTime.calendarEraName xml_buffer,
      metadata.MeasurementTimeseriesMetadata.accumulationAnchorTime.indeterminatePosition xml_char(7), metadata.MeasurementTimeseriesMetadata.accumulationIntervalLength xml_buffer, metadata.MeasurementTimeseriesMetadata.maxGapPeriod xml_buffer, metadata.TimeseriesMetadata.temporalExtent.nilReason xml_buffer, metadata.TimeseriesMetadata.temporalExtent.gml_remoteSchema xml_buffer, metadata.TimeseriesMetadata.temporalExtent.xlink_href xml_buffer, metadata.TimeseriesMetadata.temporalExtent.xlink_title xml_buffer, metadata.TimeseriesMetadata.temporalExtent.owns xml_boolean, metadata.TimeseriesMetadata.temporalExtent.gml_TimePeriod.frame xml_buffer, metadata.TimeseriesMetadata.temporalExtent.gml_TimePeriod.gml_id xml_buffer, metadata.TimeseriesMetadata.temporalExtent.gml_TimePeriod.gml_relatedTime{} xml_xml, metadata.TimeseriesMetadata.temporalExtent.gml_TimePeriod.gml_beginPosition xml_buffer, metadata.TimeseriesMetadata.temporalExtent.gml_TimePeriod.gml_beginPosition.frame xml_buffer, metadata.TimeseriesMetadata.temporalExtent.gml_TimePeriod.gml_beginPosition.calendarEraName xml_buffer, metadata.TimeseriesMetadata.temporalExtent.gml_TimePeriod.gml_beginPosition.indeterminatePosition xml_char(7), metadata.TimeseriesMetadata.temporalExtent.gml_TimePeriod.gml_begin.nilReason xml_buffer, metadata.TimeseriesMetadata.temporalExtent.gml_TimePeriod.gml_begin.gml_remoteSchema xml_buffer, metadata.TimeseriesMetadata.temporalExtent.gml_TimePeriod.gml_begin.xlink_href xml_buffer, metadata.TimeseriesMetadata.temporalExtent.gml_TimePeriod.gml_begin.xlink_title xml_buffer, metadata.TimeseriesMetadata.temporalExtent.gml_TimePeriod.gml_begin.owns xml_boolean, metadata.TimeseriesMetadata.temporalExtent.gml_TimePeriod.gml_begin.gml_TimeInstant.frame xml_buffer, metadata.TimeseriesMetadata.temporalExtent.gml_TimePeriod.gml_begin.gml_TimeInstant.gml_id xml_buffer, metadata.TimeseriesMetadata.temporalExtent.gml_TimePeriod.gml_begin.gml_TimeInstant.gml_relatedTime{} xml_xml, metadata.TimeseriesMetadata.temporalExtent.gml_TimePeriod.gml_begin.gml_TimeInstant.gml_timePosition xml_buffer, metadata.TimeseriesMetadata.temporalExtent.gml_TimePeriod.gml_begin.gml_TimeInstant.gml_timePosition.frame xml_buffer, metadata.TimeseriesMetadata.temporalExtent.gml_TimePeriod.gml_begin.gml_TimeInstant.gml_timePosition.calendarEraName xml_buffer, metadata.TimeseriesMetadata.temporalExtent.gml_TimePeriod.gml_begin.gml_TimeInstant.gml_timePosition.indeterminatePosition xml_char(7), metadata.TimeseriesMetadata.temporalExtent.gml_TimePeriod.gml_endPosition xml_buffer, metadata.TimeseriesMetadata.temporalExtent.gml_TimePeriod.gml_endPosition.frame xml_buffer, metadata.TimeseriesMetadata.temporalExtent.gml_TimePeriod.gml_endPosition.calendarEraName xml_buffer,
      metadata.TimeseriesMetadata.temporalExtent.gml_TimePeriod.gml_endPosition.indeterminatePosition xml_char(7), metadata.TimeseriesMetadata.temporalExtent.gml_TimePeriod.gml_end.nilReason xml_buffer, metadata.TimeseriesMetadata.temporalExtent.gml_TimePeriod.gml_end.gml_remoteSchema xml_buffer, metadata.TimeseriesMetadata.temporalExtent.gml_TimePeriod.gml_end.xlink_href xml_buffer, metadata.TimeseriesMetadata.temporalExtent.gml_TimePeriod.gml_end.xlink_title xml_buffer, metadata.TimeseriesMetadata.temporalExtent.gml_TimePeriod.gml_end.owns xml_boolean, metadata.TimeseriesMetadata.temporalExtent.gml_TimePeriod.gml_end.gml_TimeInstant.frame xml_buffer, metadata.TimeseriesMetadata.temporalExtent.gml_TimePeriod.gml_end.gml_TimeInstant.gml_id xml_buffer, metadata.TimeseriesMetadata.temporalExtent.gml_TimePeriod.gml_end.gml_TimeInstant.gml_relatedTime{} xml_xml, metadata.TimeseriesMetadata.temporalExtent.gml_TimePeriod.gml_end.gml_TimeInstant.gml_timePosition xml_buffer, metadata.TimeseriesMetadata.temporalExtent.gml_TimePeriod.gml_end.gml_TimeInstant.gml_timePosition.frame xml_buffer, metadata.TimeseriesMetadata.temporalExtent.gml_TimePeriod.gml_end.gml_TimeInstant.gml_timePosition.calendarEraName xml_buffer, metadata.TimeseriesMetadata.temporalExtent.gml_TimePeriod.gml_end.gml_TimeInstant.gml_timePosition.indeterminatePosition xml_char(7), metadata.TimeseriesMetadata.temporalExtent.gml_TimePeriod.gml_duration xml_buffer, metadata.TimeseriesMetadata.temporalExtent.gml_TimePeriod.gml_timeInterval xml_real64, metadata.TimeseriesMetadata.temporalExtent.gml_TimePeriod.gml_timeInterval.unit xml_buffer, metadata.TimeseriesMetadata.temporalExtent.gml_TimePeriod.gml_timeInterval.radix xml_uint64, metadata.TimeseriesMetadata.temporalExtent.gml_TimePeriod.gml_timeInterval.factor xml_int64, metadata.TimeseriesMetadata.baseTime xml_buffer, metadata.TimeseriesMetadata.baseTime.frame xml_buffer, metadata.TimeseriesMetadata.baseTime.calendarEraName xml_buffer, metadata.TimeseriesMetadata.baseTime.indeterminatePosition xml_char(7), metadata.TimeseriesMetadata.spacing xml_buffer, metadata.TimeseriesMetadata.commentBlock{}.owns xml_boolean, metadata.TimeseriesMetadata.commentBlock{}.CommentBlock.applicablePeriod.nilReason xml_buffer, metadata.TimeseriesMetadata.commentBlock{}.CommentBlock.applicablePeriod.gml_remoteSchema xml_buffer, metadata.TimeseriesMetadata.commentBlock{}.CommentBlock.applicablePeriod.xlink_href xml_buffer, metadata.TimeseriesMetadata.commentBlock{}.CommentBlock.applicablePeriod.xlink_title xml_buffer, metadata.TimeseriesMetadata.commentBlock{}.CommentBlock.applicablePeriod.owns xml_boolean, metadata.TimeseriesMetadata.commentBlock{}.CommentBlock.applicablePeriod.gml_TimePeriod.frame xml_buffer,
      metadata.TimeseriesMetadata.commentBlock{}.CommentBlock.applicablePeriod.gml_TimePeriod.gml_id xml_buffer, metadata.TimeseriesMetadata.commentBlock{}.CommentBlock.applicablePeriod.gml_TimePeriod.gml_relatedTime{} xml_xml, metadata.TimeseriesMetadata.commentBlock{}.CommentBlock.applicablePeriod.gml_TimePeriod.gml_beginPosition xml_buffer, metadata.TimeseriesMetadata.commentBlock{}.CommentBlock.applicablePeriod.gml_TimePeriod.gml_beginPosition.frame xml_buffer, metadata.TimeseriesMetadata.commentBlock{}.CommentBlock.applicablePeriod.gml_TimePeriod.gml_beginPosition.calendarEraName xml_buffer, metadata.TimeseriesMetadata.commentBlock{}.CommentBlock.applicablePeriod.gml_TimePeriod.gml_beginPosition.indeterminatePosition xml_char(7), metadata.TimeseriesMetadata.commentBlock{}.CommentBlock.applicablePeriod.gml_TimePeriod.gml_begin.nilReason xml_buffer, metadata.TimeseriesMetadata.commentBlock{}.CommentBlock.applicablePeriod.gml_TimePeriod.gml_begin.gml_remoteSchema xml_buffer, metadata.TimeseriesMetadata.commentBlock{}.CommentBlock.applicablePeriod.gml_TimePeriod.gml_begin.xlink_href xml_buffer, metadata.TimeseriesMetadata.commentBlock{}.CommentBlock.applicablePeriod.gml_TimePeriod.gml_begin.xlink_title xml_buffer, metadata.TimeseriesMetadata.commentBlock{}.CommentBlock.applicablePeriod.gml_TimePeriod.gml_begin.owns xml_boolean, metadata.TimeseriesMetadata.commentBlock{}.CommentBlock.applicablePeriod.gml_TimePeriod.gml_begin.gml_TimeInstant.frame xml_buffer, metadata.TimeseriesMetadata.commentBlock{}.CommentBlock.applicablePeriod.gml_TimePeriod.gml_begin.gml_TimeInstant.gml_id xml_buffer, metadata.TimeseriesMetadata.commentBlock{}.CommentBlock.applicablePeriod.gml_TimePeriod.gml_begin.gml_TimeInstant.gml_relatedTime{} xml_xml, metadata.TimeseriesMetadata.commentBlock{}.CommentBlock.applicablePeriod.gml_TimePeriod.gml_begin.gml_TimeInstant.gml_timePosition xml_buffer, metadata.TimeseriesMetadata.commentBlock{}.CommentBlock.applicablePeriod.gml_TimePeriod.gml_begin.gml_TimeInstant.gml_timePosition.frame xml_buffer, metadata.TimeseriesMetadata.commentBlock{}.CommentBlock.applicablePeriod.gml_TimePeriod.gml_begin.gml_TimeInstant.gml_timePosition.calendarEraName xml_buffer, metadata.TimeseriesMetadata.commentBlock{}.CommentBlock.applicablePeriod.gml_TimePeriod.gml_begin.gml_TimeInstant.gml_timePosition.indeterminatePosition xml_char(7), metadata.TimeseriesMetadata.commentBlock{}.CommentBlock.applicablePeriod.gml_TimePeriod.gml_endPosition xml_buffer, metadata.TimeseriesMetadata.commentBlock{}.CommentBlock.applicablePeriod.gml_TimePeriod.gml_endPosition.frame xml_buffer, metadata.TimeseriesMetadata.commentBlock{}.CommentBlock.applicablePeriod.gml_TimePeriod.gml_endPosition.calendarEraName xml_buffer, metadata.TimeseriesMetadata.commentBlock{}.CommentBlock.applicablePeriod.gml_TimePeriod.gml_endPosition.indeterminatePosition xml_char(7), metadata.TimeseriesMetadata.commentBlock{}.CommentBlock.applicablePeriod.gml_TimePeriod.gml_end.nilReason xml_buffer, metadata.TimeseriesMetadata.commentBlock{}.CommentBlock.applicablePeriod.gml_TimePeriod.gml_end.gml_remoteSchema xml_buffer, metadata.TimeseriesMetadata.commentBlock{}.CommentBlock.applicablePeriod.gml_TimePeriod.gml_end.xlink_href xml_buffer, metadata.TimeseriesMetadata.commentBlock{}.CommentBlock.applicablePeriod.gml_TimePeriod.gml_end.xlink_title xml_buffer, metadata.TimeseriesMetadata.commentBlock{}.CommentBlock.applicablePeriod.gml_TimePeriod.gml_end.owns xml_boolean, metadata.TimeseriesMetadata.commentBlock{}.CommentBlock.applicablePeriod.gml_TimePeriod.gml_end.gml_TimeInstant.frame xml_buffer, metadata.TimeseriesMetadata.commentBlock{}.CommentBlock.applicablePeriod.gml_TimePeriod.gml_end.gml_TimeInstant.gml_id xml_buffer, metadata.TimeseriesMetadata.commentBlock{}.CommentBlock.applicablePeriod.gml_TimePeriod.gml_end.gml_TimeInstant.gml_relatedTime{} xml_xml,
      metadata.TimeseriesMetadata.commentBlock{}.CommentBlock.applicablePeriod.gml_TimePeriod.gml_end.gml_TimeInstant.gml_timePosition xml_buffer, metadata.TimeseriesMetadata.commentBlock{}.CommentBlock.applicablePeriod.gml_TimePeriod.gml_end.gml_TimeInstant.gml_timePosition.frame xml_buffer, metadata.TimeseriesMetadata.commentBlock{}.CommentBlock.applicablePeriod.gml_TimePeriod.gml_end.gml_TimeInstant.gml_timePosition.calendarEraName xml_buffer, metadata.TimeseriesMetadata.commentBlock{}.CommentBlock.applicablePeriod.gml_TimePeriod.gml_end.gml_TimeInstant.gml_timePosition.indeterminatePosition xml_char(7), metadata.TimeseriesMetadata.commentBlock{}.CommentBlock.applicablePeriod.gml_TimePeriod.gml_duration xml_buffer, metadata.TimeseriesMetadata.commentBlock{}.CommentBlock.applicablePeriod.gml_TimePeriod.gml_timeInterval xml_real64, metadata.TimeseriesMetadata.commentBlock{}.CommentBlock.applicablePeriod.gml_TimePeriod.gml_timeInterval.unit xml_buffer, metadata.TimeseriesMetadata.commentBlock{}.CommentBlock.applicablePeriod.gml_TimePeriod.gml_timeInterval.radix xml_uint64, metadata.TimeseriesMetadata.commentBlock{}.CommentBlock.applicablePeriod.gml_TimePeriod.gml_timeInterval.factor xml_int64, metadata.TimeseriesMetadata.commentBlock{}.CommentBlock.comment xml_buffer, metadata.TimeseriesMetadata.parameter{}.nilReason xml_buffer, metadata.TimeseriesMetadata.parameter{}.gml_remoteSchema xml_buffer, metadata.TimeseriesMetadata.parameter{}.xlink_href xml_buffer, metadata.TimeseriesMetadata.parameter{}.xlink_title xml_buffer, metadata.TimeseriesMetadata.parameter{}.NamedValue.name.owns xml_boolean, metadata.TimeseriesMetadata.parameter{}.NamedValue.name.nilReason xml_buffer, metadata.TimeseriesMetadata.parameter{}.NamedValue.name.gml_remoteSchema xml_buffer, metadata.TimeseriesMetadata.parameter{}.NamedValue.name.xlink_href xml_buffer, metadata.TimeseriesMetadata.parameter{}.NamedValue.name.xlink_title xml_buffer, metadata.TimeseriesMetadata.parameter{}.NamedValue.value xml_xml, defaultPointMetadata{} xml_xml, defaultPointMetadata{}.owns xml_boolean, point{}.MeasurementTVP.time xml_buffer, point{}.MeasurementTVP.time.frame xml_buffer, point{}.MeasurementTVP.time.calendarEraName xml_buffer, point{}.MeasurementTVP.time.indeterminatePosition xml_char(7), point{}.MeasurementTVP.value xml_real64, point{}.MeasurementTVP.value.uom xml_buffer, point{}.MeasurementTVP.value.xsi_nil xml_boolean, point{}.MeasurementTVP.metadata.owns xml_boolean,
      point{}.MeasurementTVP.metadata.TVPMeasurementMetadata.quality.owns xml_boolean, point{}.MeasurementTVP.metadata.TVPMeasurementMetadata.quality.nilReason xml_buffer, point{}.MeasurementTVP.metadata.TVPMeasurementMetadata.quality.gml_remoteSchema xml_buffer, point{}.MeasurementTVP.metadata.TVPMeasurementMetadata.quality.xlink_href xml_buffer, point{}.MeasurementTVP.metadata.TVPMeasurementMetadata.quality.xlink_title xml_buffer, point{}.MeasurementTVP.metadata.TVPMeasurementMetadata.nilReason.owns xml_boolean, point{}.MeasurementTVP.metadata.TVPMeasurementMetadata.nilReason.nilReason xml_buffer, point{}.MeasurementTVP.metadata.TVPMeasurementMetadata.nilReason.gml_remoteSchema xml_buffer, point{}.MeasurementTVP.metadata.TVPMeasurementMetadata.nilReason.xlink_href xml_buffer, point{}.MeasurementTVP.metadata.TVPMeasurementMetadata.nilReason.xlink_title xml_buffer, point{}.MeasurementTVP.metadata.TVPMeasurementMetadata.comment xml_buffer, point{}.MeasurementTVP.metadata.TVPMeasurementMetadata.relatedObservation{}.ObservationContext.role.owns xml_boolean, point{}.MeasurementTVP.metadata.TVPMeasurementMetadata.relatedObservation{}.ObservationContext.role.nilReason xml_buffer, point{}.MeasurementTVP.metadata.TVPMeasurementMetadata.relatedObservation{}.ObservationContext.role.gml_remoteSchema xml_buffer, point{}.MeasurementTVP.metadata.TVPMeasurementMetadata.relatedObservation{}.ObservationContext.role.xlink_href xml_buffer, point{}.MeasurementTVP.metadata.TVPMeasurementMetadata.relatedObservation{}.ObservationContext.role.xlink_title xml_buffer, point{}.MeasurementTVP.metadata.TVPMeasurementMetadata.relatedObservation{}.ObservationContext.relatedObservation.owns xml_boolean, point{}.MeasurementTVP.metadata.TVPMeasurementMetadata.relatedObservation{}.ObservationContext.relatedObservation.nilReason xml_buffer, point{}.MeasurementTVP.metadata.TVPMeasurementMetadata.relatedObservation{}.ObservationContext.relatedObservation.gml_remoteSchema xml_buffer, point{}.MeasurementTVP.metadata.TVPMeasurementMetadata.relatedObservation{}.ObservationContext.relatedObservation.xlink_href xml_buffer, point{}.MeasurementTVP.metadata.TVPMeasurementMetadata.relatedObservation{}.ObservationContext.relatedObservation.xlink_title xml_buffer, point{}.MeasurementTVP.metadata.TVPMeasurementMetadata.qualifier{}.xlink_href xml_buffer, point{}.MeasurementTVP.metadata.TVPMeasurementMetadata.qualifier{}.xlink_title xml_buffer, point{}.MeasurementTVP.metadata.TVPMeasurementMetadata.qualifier{}.Quantity.referenceFrame xml_buffer, point{}.MeasurementTVP.metadata.TVPMeasurementMetadata.qualifier{}.Quantity.axisID xml_buffer, point{}.MeasurementTVP.metadata.TVPMeasurementMetadata.qualifier{}.Quantity.updatable xml_boolean, point{}.MeasurementTVP.metadata.TVPMeasurementMetadata.qualifier{}.Quantity.optional xml_boolean, point{}.MeasurementTVP.metadata.TVPMeasurementMetadata.qualifier{}.Quantity.definition xml_buffer, point{}.MeasurementTVP.metadata.TVPMeasurementMetadata.qualifier{}.Quantity.id xml_buffer, point{}.MeasurementTVP.metadata.TVPMeasurementMetadata.qualifier{}.Quantity.extension{} xml_xml,
      point{}.MeasurementTVP.metadata.TVPMeasurementMetadata.qualifier{}.Quantity.identifier xml_buffer, point{}.MeasurementTVP.metadata.TVPMeasurementMetadata.qualifier{}.Quantity.label xml_buffer, point{}.MeasurementTVP.metadata.TVPMeasurementMetadata.qualifier{}.Quantity.description xml_buffer, point{}.MeasurementTVP.metadata.TVPMeasurementMetadata.qualifier{}.Quantity.quality{}.xlink_href xml_buffer, point{}.MeasurementTVP.metadata.TVPMeasurementMetadata.qualifier{}.Quantity.quality{}.xlink_title xml_buffer, point{}.MeasurementTVP.metadata.TVPMeasurementMetadata.qualifier{}.Quantity.quality{}.Quantity xml_xml, point{}.MeasurementTVP.metadata.TVPMeasurementMetadata.qualifier{}.Quantity.quality{}.Quantity.referenceFrame xml_buffer, point{}.MeasurementTVP.metadata.TVPMeasurementMetadata.qualifier{}.Quantity.quality{}.Quantity.axisID xml_buffer, point{}.MeasurementTVP.metadata.TVPMeasurementMetadata.qualifier{}.Quantity.quality{}.Quantity.updatable xml_boolean, point{}.MeasurementTVP.metadata.TVPMeasurementMetadata.qualifier{}.Quantity.quality{}.Quantity.optional xml_boolean, point{}.MeasurementTVP.metadata.TVPMeasurementMetadata.qualifier{}.Quantity.quality{}.Quantity.definition xml_buffer, point{}.MeasurementTVP.metadata.TVPMeasurementMetadata.qualifier{}.Quantity.quality{}.Quantity.id xml_buffer, point{}.MeasurementTVP.metadata.TVPMeasurementMetadata.qualifier{}.Quantity.quality{}.QuantityRange.referenceFrame xml_buffer, point{}.MeasurementTVP.metadata.TVPMeasurementMetadata.qualifier{}.Quantity.quality{}.QuantityRange.axisID xml_buffer, point{}.MeasurementTVP.metadata.TVPMeasurementMetadata.qualifier{}.Quantity.quality{}.QuantityRange.updatable xml_boolean, point{}.MeasurementTVP.metadata.TVPMeasurementMetadata.qualifier{}.Quantity.quality{}.QuantityRange.optional xml_boolean, point{}.MeasurementTVP.metadata.TVPMeasurementMetadata.qualifier{}.Quantity.quality{}.QuantityRange.definition xml_buffer, point{}.MeasurementTVP.metadata.TVPMeasurementMetadata.qualifier{}.Quantity.quality{}.QuantityRange.id xml_buffer, point{}.MeasurementTVP.metadata.TVPMeasurementMetadata.qualifier{}.Quantity.quality{}.QuantityRange.extension{} xml_xml, point{}.MeasurementTVP.metadata.TVPMeasurementMetadata.qualifier{}.Quantity.quality{}.QuantityRange.identifier xml_buffer, point{}.MeasurementTVP.metadata.TVPMeasurementMetadata.qualifier{}.Quantity.quality{}.QuantityRange.label xml_buffer, point{}.MeasurementTVP.metadata.TVPMeasurementMetadata.qualifier{}.Quantity.quality{}.QuantityRange.description xml_buffer, point{}.MeasurementTVP.metadata.TVPMeasurementMetadata.qualifier{}.Quantity.quality{}.QuantityRange.quality{} xml_xml, point{}.MeasurementTVP.metadata.TVPMeasurementMetadata.qualifier{}.Quantity.quality{}.QuantityRange.quality{}.xlink_href xml_buffer, point{}.MeasurementTVP.metadata.TVPMeasurementMetadata.qualifier{}.Quantity.quality{}.QuantityRange.quality{}.xlink_title xml_buffer, point{}.MeasurementTVP.metadata.TVPMeasurementMetadata.qualifier{}.Quantity.quality{}.QuantityRange.nilValues.xlink_href xml_buffer, point{}.MeasurementTVP.metadata.TVPMeasurementMetadata.qualifier{}.Quantity.quality{}.QuantityRange.nilValues.xlink_title xml_buffer, point{}.MeasurementTVP.metadata.TVPMeasurementMetadata.qualifier{}.Quantity.quality{}.QuantityRange.nilValues.NilValues.id xml_buffer, point{}.MeasurementTVP.metadata.TVPMeasurementMetadata.qualifier{}.Quantity.quality{}.QuantityRange.nilValues.NilValues.extension{} xml_xml, point{}.MeasurementTVP.metadata.TVPMeasurementMetadata.qualifier{}.Quantity.quality{}.QuantityRange.nilValues.NilValues.nilValue{} xml_buffer,
      point{}.MeasurementTVP.metadata.TVPMeasurementMetadata.qualifier{}.Quantity.quality{}.QuantityRange.nilValues.NilValues.nilValue{}.reason xml_buffer, point{}.MeasurementTVP.metadata.TVPMeasurementMetadata.qualifier{}.Quantity.quality{}.QuantityRange.uom.code xml_buffer, point{}.MeasurementTVP.metadata.TVPMeasurementMetadata.qualifier{}.Quantity.quality{}.QuantityRange.uom.xlink_href xml_buffer, point{}.MeasurementTVP.metadata.TVPMeasurementMetadata.qualifier{}.Quantity.quality{}.QuantityRange.uom.xlink_title xml_buffer, point{}.MeasurementTVP.metadata.TVPMeasurementMetadata.qualifier{}.Quantity.quality{}.QuantityRange.constraint.xlink_href xml_buffer, point{}.MeasurementTVP.metadata.TVPMeasurementMetadata.qualifier{}.Quantity.quality{}.QuantityRange.constraint.xlink_title xml_buffer, point{}.MeasurementTVP.metadata.TVPMeasurementMetadata.qualifier{}.Quantity.quality{}.QuantityRange.constraint.AllowedValues.id xml_buffer, point{}.MeasurementTVP.metadata.TVPMeasurementMetadata.qualifier{}.Quantity.quality{}.QuantityRange.constraint.AllowedValues.extension{} xml_xml, point{}.MeasurementTVP.metadata.TVPMeasurementMetadata.qualifier{}.Quantity.quality{}.QuantityRange.constraint.AllowedValues.value{} xml_real64, point{}.MeasurementTVP.metadata.TVPMeasurementMetadata.qualifier{}.Quantity.quality{}.QuantityRange.constraint.AllowedValues.interval{} xml_buffer, point{}.MeasurementTVP.metadata.TVPMeasurementMetadata.qualifier{}.Quantity.quality{}.QuantityRange.constraint.AllowedValues.significantFigures xml_int64, point{}.MeasurementTVP.metadata.TVPMeasurementMetadata.qualifier{}.Quantity.quality{}.QuantityRange.value xml_buffer, point{}.MeasurementTVP.metadata.TVPMeasurementMetadata.qualifier{}.Quantity.quality{}.Category.referenceFrame xml_buffer, point{}.MeasurementTVP.metadata.TVPMeasurementMetadata.qualifier{}.Quantity.quality{}.Category.axisID xml_buffer, point{}.MeasurementTVP.metadata.TVPMeasurementMetadata.qualifier{}.Quantity.quality{}.Category.updatable xml_boolean, point{}.MeasurementTVP.metadata.TVPMeasurementMetadata.qualifier{}.Quantity.quality{}.Category.optional xml_boolean, point{}.MeasurementTVP.metadata.TVPMeasurementMetadata.qualifier{}.Quantity.quality{}.Category.definition xml_buffer, point{}.MeasurementTVP.metadata.TVPMeasurementMetadata.qualifier{}.Quantity.quality{}.Category.id xml_buffer, point{}.MeasurementTVP.metadata.TVPMeasurementMetadata.qualifier{}.Quantity.quality{}.Category.extension{} xml_xml, point{}.MeasurementTVP.metadata.TVPMeasurementMetadata.qualifier{}.Quantity.quality{}.Category.identifier xml_buffer, point{}.MeasurementTVP.metadata.TVPMeasurementMetadata.qualifier{}.Quantity.quality{}.Category.label xml_buffer, point{}.MeasurementTVP.metadata.TVPMeasurementMetadata.qualifier{}.Quantity.quality{}.Category.description xml_buffer, point{}.MeasurementTVP.metadata.TVPMeasurementMetadata.qualifier{}.Quantity.quality{}.Category.quality{} xml_xml, point{}.MeasurementTVP.metadata.TVPMeasurementMetadata.qualifier{}.Quantity.quality{}.Category.quality{}.xlink_href xml_buffer, point{}.MeasurementTVP.metadata.TVPMeasurementMetadata.qualifier{}.Quantity.quality{}.Category.quality{}.xlink_title xml_buffer, point{}.MeasurementTVP.metadata.TVPMeasurementMetadata.qualifier{}.Quantity.quality{}.Category.nilValues.xlink_href xml_buffer, point{}.MeasurementTVP.metadata.TVPMeasurementMetadata.qualifier{}.Quantity.quality{}.Category.nilValues.xlink_title xml_buffer, point{}.MeasurementTVP.metadata.TVPMeasurementMetadata.qualifier{}.Quantity.quality{}.Category.nilValues.NilValues.id xml_buffer, point{}.MeasurementTVP.metadata.TVPMeasurementMetadata.qualifier{}.Quantity.quality{}.Category.nilValues.NilValues.extension{} xml_xml, point{}.MeasurementTVP.metadata.TVPMeasurementMetadata.qualifier{}.Quantity.quality{}.Category.nilValues.NilValues.nilValue{} xml_buffer,
      point{}.MeasurementTVP.metadata.TVPMeasurementMetadata.qualifier{}.Quantity.quality{}.Category.nilValues.NilValues.nilValue{}.reason xml_buffer, point{}.MeasurementTVP.metadata.TVPMeasurementMetadata.qualifier{}.Quantity.quality{}.Category.codeSpace.xlink_href xml_buffer, point{}.MeasurementTVP.metadata.TVPMeasurementMetadata.qualifier{}.Quantity.quality{}.Category.codeSpace.xlink_title xml_buffer, point{}.MeasurementTVP.metadata.TVPMeasurementMetadata.qualifier{}.Quantity.quality{}.Category.constraint.xlink_href xml_buffer, point{}.MeasurementTVP.metadata.TVPMeasurementMetadata.qualifier{}.Quantity.quality{}.Category.constraint.xlink_title xml_buffer, point{}.MeasurementTVP.metadata.TVPMeasurementMetadata.qualifier{}.Quantity.quality{}.Category.constraint.AllowedTokens.id xml_buffer, point{}.MeasurementTVP.metadata.TVPMeasurementMetadata.qualifier{}.Quantity.quality{}.Category.constraint.AllowedTokens.extension{} xml_xml, point{}.MeasurementTVP.metadata.TVPMeasurementMetadata.qualifier{}.Quantity.quality{}.Category.constraint.AllowedTokens.value{} xml_buffer, point{}.MeasurementTVP.metadata.TVPMeasurementMetadata.qualifier{}.Quantity.quality{}.Category.constraint.AllowedTokens.pattern xml_buffer, point{}.MeasurementTVP.metadata.TVPMeasurementMetadata.qualifier{}.Quantity.quality{}.Category.value xml_buffer, point{}.MeasurementTVP.metadata.TVPMeasurementMetadata.qualifier{}.Quantity.quality{}.Text.referenceFrame xml_buffer, point{}.MeasurementTVP.metadata.TVPMeasurementMetadata.qualifier{}.Quantity.quality{}.Text.axisID xml_buffer, point{}.MeasurementTVP.metadata.TVPMeasurementMetadata.qualifier{}.Quantity.quality{}.Text.updatable xml_boolean, point{}.MeasurementTVP.metadata.TVPMeasurementMetadata.qualifier{}.Quantity.quality{}.Text.optional xml_boolean, point{}.MeasurementTVP.metadata.TVPMeasurementMetadata.qualifier{}.Quantity.quality{}.Text.definition xml_buffer, point{}.MeasurementTVP.metadata.TVPMeasurementMetadata.qualifier{}.Quantity.quality{}.Text.id xml_buffer, point{}.MeasurementTVP.metadata.TVPMeasurementMetadata.qualifier{}.Quantity.quality{}.Text.extension{} xml_xml, point{}.MeasurementTVP.metadata.TVPMeasurementMetadata.qualifier{}.Quantity.quality{}.Text.identifier xml_buffer, point{}.MeasurementTVP.metadata.TVPMeasurementMetadata.qualifier{}.Quantity.quality{}.Text.label xml_buffer, point{}.MeasurementTVP.metadata.TVPMeasurementMetadata.qualifier{}.Quantity.quality{}.Text.description xml_buffer, point{}.MeasurementTVP.metadata.TVPMeasurementMetadata.qualifier{}.Quantity.quality{}.Text.quality{} xml_xml, point{}.MeasurementTVP.metadata.TVPMeasurementMetadata.qualifier{}.Quantity.quality{}.Text.quality{}.xlink_href xml_buffer, point{}.MeasurementTVP.metadata.TVPMeasurementMetadata.qualifier{}.Quantity.quality{}.Text.quality{}.xlink_title xml_buffer, point{}.MeasurementTVP.metadata.TVPMeasurementMetadata.qualifier{}.Quantity.quality{}.Text.nilValues.xlink_href xml_buffer, point{}.MeasurementTVP.metadata.TVPMeasurementMetadata.qualifier{}.Quantity.quality{}.Text.nilValues.xlink_title xml_buffer, point{}.MeasurementTVP.metadata.TVPMeasurementMetadata.qualifier{}.Quantity.quality{}.Text.nilValues.NilValues.id xml_buffer, point{}.MeasurementTVP.metadata.TVPMeasurementMetadata.qualifier{}.Quantity.quality{}.Text.nilValues.NilValues.extension{} xml_xml, point{}.MeasurementTVP.metadata.TVPMeasurementMetadata.qualifier{}.Quantity.quality{}.Text.nilValues.NilValues.nilValue{} xml_buffer, point{}.MeasurementTVP.metadata.TVPMeasurementMetadata.qualifier{}.Quantity.quality{}.Text.nilValues.NilValues.nilValue{}.reason xml_buffer, point{}.MeasurementTVP.metadata.TVPMeasurementMetadata.qualifier{}.Quantity.quality{}.Text.constraint.xlink_href xml_buffer,
      point{}.MeasurementTVP.metadata.TVPMeasurementMetadata.qualifier{}.Quantity.quality{}.Text.constraint.xlink_title xml_buffer, point{}.MeasurementTVP.metadata.TVPMeasurementMetadata.qualifier{}.Quantity.quality{}.Text.constraint.AllowedTokens.id xml_buffer, point{}.MeasurementTVP.metadata.TVPMeasurementMetadata.qualifier{}.Quantity.quality{}.Text.constraint.AllowedTokens.extension{} xml_xml, point{}.MeasurementTVP.metadata.TVPMeasurementMetadata.qualifier{}.Quantity.quality{}.Text.constraint.AllowedTokens.value{} xml_buffer, point{}.MeasurementTVP.metadata.TVPMeasurementMetadata.qualifier{}.Quantity.quality{}.Text.constraint.AllowedTokens.pattern xml_buffer, point{}.MeasurementTVP.metadata.TVPMeasurementMetadata.qualifier{}.Quantity.quality{}.Text.value xml_buffer, point{}.MeasurementTVP.metadata.TVPMeasurementMetadata.qualifier{}.Quantity.nilValues.xlink_href xml_buffer, point{}.MeasurementTVP.metadata.TVPMeasurementMetadata.qualifier{}.Quantity.nilValues.xlink_title xml_buffer, point{}.MeasurementTVP.metadata.TVPMeasurementMetadata.qualifier{}.Quantity.nilValues.NilValues.id xml_buffer, point{}.MeasurementTVP.metadata.TVPMeasurementMetadata.qualifier{}.Quantity.nilValues.NilValues.extension{} xml_xml, point{}.MeasurementTVP.metadata.TVPMeasurementMetadata.qualifier{}.Quantity.nilValues.NilValues.nilValue{} xml_buffer, point{}.MeasurementTVP.metadata.TVPMeasurementMetadata.qualifier{}.Quantity.nilValues.NilValues.nilValue{}.reason xml_buffer, point{}.MeasurementTVP.metadata.TVPMeasurementMetadata.qualifier{}.Quantity.uom.code xml_buffer, point{}.MeasurementTVP.metadata.TVPMeasurementMetadata.qualifier{}.Quantity.uom.xlink_href xml_buffer, point{}.MeasurementTVP.metadata.TVPMeasurementMetadata.qualifier{}.Quantity.uom.xlink_title xml_buffer, point{}.MeasurementTVP.metadata.TVPMeasurementMetadata.qualifier{}.Quantity.constraint.xlink_href xml_buffer, point{}.MeasurementTVP.metadata.TVPMeasurementMetadata.qualifier{}.Quantity.constraint.xlink_title xml_buffer, point{}.MeasurementTVP.metadata.TVPMeasurementMetadata.qualifier{}.Quantity.constraint.AllowedValues.id xml_buffer, point{}.MeasurementTVP.metadata.TVPMeasurementMetadata.qualifier{}.Quantity.constraint.AllowedValues.extension{} xml_xml, point{}.MeasurementTVP.metadata.TVPMeasurementMetadata.qualifier{}.Quantity.constraint.AllowedValues.value{} xml_real64, point{}.MeasurementTVP.metadata.TVPMeasurementMetadata.qualifier{}.Quantity.constraint.AllowedValues.interval{} xml_buffer, point{}.MeasurementTVP.metadata.TVPMeasurementMetadata.qualifier{}.Quantity.constraint.AllowedValues.significantFigures xml_int64, point{}.MeasurementTVP.metadata.TVPMeasurementMetadata.qualifier{}.Quantity.value xml_real64, point{}.MeasurementTVP.metadata.TVPMeasurementMetadata.qualifier{}.QuantityRange.referenceFrame xml_buffer, point{}.MeasurementTVP.metadata.TVPMeasurementMetadata.qualifier{}.QuantityRange.axisID xml_buffer, point{}.MeasurementTVP.metadata.TVPMeasurementMetadata.qualifier{}.QuantityRange.updatable xml_boolean, point{}.MeasurementTVP.metadata.TVPMeasurementMetadata.qualifier{}.QuantityRange.optional xml_boolean, point{}.MeasurementTVP.metadata.TVPMeasurementMetadata.qualifier{}.QuantityRange.definition xml_buffer, point{}.MeasurementTVP.metadata.TVPMeasurementMetadata.qualifier{}.QuantityRange.id xml_buffer, point{}.MeasurementTVP.metadata.TVPMeasurementMetadata.qualifier{}.QuantityRange.extension{} xml_xml,
      point{}.MeasurementTVP.metadata.TVPMeasurementMetadata.qualifier{}.QuantityRange.identifier xml_buffer, point{}.MeasurementTVP.metadata.TVPMeasurementMetadata.qualifier{}.QuantityRange.label xml_buffer, point{}.MeasurementTVP.metadata.TVPMeasurementMetadata.qualifier{}.QuantityRange.description xml_buffer, point{}.MeasurementTVP.metadata.TVPMeasurementMetadata.qualifier{}.QuantityRange.quality{}.xlink_href xml_buffer, point{}.MeasurementTVP.metadata.TVPMeasurementMetadata.qualifier{}.QuantityRange.quality{}.xlink_title xml_buffer, point{}.MeasurementTVP.metadata.TVPMeasurementMetadata.qualifier{}.QuantityRange.quality{}.Quantity.referenceFrame xml_buffer, point{}.MeasurementTVP.metadata.TVPMeasurementMetadata.qualifier{}.QuantityRange.quality{}.Quantity.axisID xml_buffer, point{}.MeasurementTVP.metadata.TVPMeasurementMetadata.qualifier{}.QuantityRange.quality{}.Quantity.updatable xml_boolean, point{}.MeasurementTVP.metadata.TVPMeasurementMetadata.qualifier{}.QuantityRange.quality{}.Quantity.optional xml_boolean, point{}.MeasurementTVP.metadata.TVPMeasurementMetadata.qualifier{}.QuantityRange.quality{}.Quantity.definition xml_buffer, point{}.MeasurementTVP.metadata.TVPMeasurementMetadata.qualifier{}.QuantityRange.quality{}.Quantity.id xml_buffer, point{}.MeasurementTVP.metadata.TVPMeasurementMetadata.qualifier{}.QuantityRange.quality{}.Quantity.extension{} xml_xml, point{}.MeasurementTVP.metadata.TVPMeasurementMetadata.qualifier{}.QuantityRange.quality{}.Quantity.identifier xml_buffer, point{}.MeasurementTVP.metadata.TVPMeasurementMetadata.qualifier{}.QuantityRange.quality{}.Quantity.label xml_buffer, point{}.MeasurementTVP.metadata.TVPMeasurementMetadata.qualifier{}.QuantityRange.quality{}.Quantity.description xml_buffer, point{}.MeasurementTVP.metadata.TVPMeasurementMetadata.qualifier{}.QuantityRange.quality{}.Quantity.quality{} xml_xml, point{}.MeasurementTVP.metadata.TVPMeasurementMetadata.qualifier{}.QuantityRange.quality{}.Quantity.quality{}.xlink_href xml_buffer, point{}.MeasurementTVP.metadata.TVPMeasurementMetadata.qualifier{}.QuantityRange.quality{}.Quantity.quality{}.xlink_title xml_buffer, point{}.MeasurementTVP.metadata.TVPMeasurementMetadata.qualifier{}.QuantityRange.quality{}.Quantity.nilValues.xlink_href xml_buffer, point{}.MeasurementTVP.metadata.TVPMeasurementMetadata.qualifier{}.QuantityRange.quality{}.Quantity.nilValues.xlink_title xml_buffer, point{}.MeasurementTVP.metadata.TVPMeasurementMetadata.qualifier{}.QuantityRange.quality{}.Quantity.nilValues.NilValues.id xml_buffer, point{}.MeasurementTVP.metadata.TVPMeasurementMetadata.qualifier{}.QuantityRange.quality{}.Quantity.nilValues.NilValues.extension{} xml_xml, point{}.MeasurementTVP.metadata.TVPMeasurementMetadata.qualifier{}.QuantityRange.quality{}.Quantity.nilValues.NilValues.nilValue{} xml_buffer, point{}.MeasurementTVP.metadata.TVPMeasurementMetadata.qualifier{}.QuantityRange.quality{}.Quantity.nilValues.NilValues.nilValue{}.reason xml_buffer, point{}.MeasurementTVP.metadata.TVPMeasurementMetadata.qualifier{}.QuantityRange.quality{}.Quantity.uom.code xml_buffer, point{}.MeasurementTVP.metadata.TVPMeasurementMetadata.qualifier{}.QuantityRange.quality{}.Quantity.uom.xlink_href xml_buffer, point{}.MeasurementTVP.metadata.TVPMeasurementMetadata.qualifier{}.QuantityRange.quality{}.Quantity.uom.xlink_title xml_buffer, point{}.MeasurementTVP.metadata.TVPMeasurementMetadata.qualifier{}.QuantityRange.quality{}.Quantity.constraint.xlink_href xml_buffer, point{}.MeasurementTVP.metadata.TVPMeasurementMetadata.qualifier{}.QuantityRange.quality{}.Quantity.constraint.xlink_title xml_buffer, point{}.MeasurementTVP.metadata.TVPMeasurementMetadata.qualifier{}.QuantityRange.quality{}.Quantity.constraint.AllowedValues.id xml_buffer,
      point{}.MeasurementTVP.metadata.TVPMeasurementMetadata.qualifier{}.QuantityRange.quality{}.Quantity.constraint.AllowedValues.extension{} xml_xml, point{}.MeasurementTVP.metadata.TVPMeasurementMetadata.qualifier{}.QuantityRange.quality{}.Quantity.constraint.AllowedValues.value{} xml_real64, point{}.MeasurementTVP.metadata.TVPMeasurementMetadata.qualifier{}.QuantityRange.quality{}.Quantity.constraint.AllowedValues.interval{} xml_buffer, point{}.MeasurementTVP.metadata.TVPMeasurementMetadata.qualifier{}.QuantityRange.quality{}.Quantity.constraint.AllowedValues.significantFigures xml_int64, point{}.MeasurementTVP.metadata.TVPMeasurementMetadata.qualifier{}.QuantityRange.quality{}.Quantity.value xml_real64, point{}.MeasurementTVP.metadata.TVPMeasurementMetadata.qualifier{}.QuantityRange.quality{}.QuantityRange xml_xml, point{}.MeasurementTVP.metadata.TVPMeasurementMetadata.qualifier{}.QuantityRange.quality{}.QuantityRange.referenceFrame xml_buffer, point{}.MeasurementTVP.metadata.TVPMeasurementMetadata.qualifier{}.QuantityRange.quality{}.QuantityRange.axisID xml_buffer, point{}.MeasurementTVP.metadata.TVPMeasurementMetadata.qualifier{}.QuantityRange.quality{}.QuantityRange.updatable xml_boolean, point{}.MeasurementTVP.metadata.TVPMeasurementMetadata.qualifier{}.QuantityRange.quality{}.QuantityRange.optional xml_boolean, point{}.MeasurementTVP.metadata.TVPMeasurementMetadata.qualifier{}.QuantityRange.quality{}.QuantityRange.definition xml_buffer, point{}.MeasurementTVP.metadata.TVPMeasurementMetadata.qualifier{}.QuantityRange.quality{}.QuantityRange.id xml_buffer, point{}.MeasurementTVP.metadata.TVPMeasurementMetadata.qualifier{}.QuantityRange.quality{}.Category.referenceFrame xml_buffer, point{}.MeasurementTVP.metadata.TVPMeasurementMetadata.qualifier{}.QuantityRange.quality{}.Category.axisID xml_buffer, point{}.MeasurementTVP.metadata.TVPMeasurementMetadata.qualifier{}.QuantityRange.quality{}.Category.updatable xml_boolean, point{}.MeasurementTVP.metadata.TVPMeasurementMetadata.qualifier{}.QuantityRange.quality{}.Category.optional xml_boolean, point{}.MeasurementTVP.metadata.TVPMeasurementMetadata.qualifier{}.QuantityRange.quality{}.Category.definition xml_buffer, point{}.MeasurementTVP.metadata.TVPMeasurementMetadata.qualifier{}.QuantityRange.quality{}.Category.id xml_buffer, point{}.MeasurementTVP.metadata.TVPMeasurementMetadata.qualifier{}.QuantityRange.quality{}.Category.extension{} xml_xml, point{}.MeasurementTVP.metadata.TVPMeasurementMetadata.qualifier{}.QuantityRange.quality{}.Category.identifier xml_buffer, point{}.MeasurementTVP.metadata.TVPMeasurementMetadata.qualifier{}.QuantityRange.quality{}.Category.label xml_buffer, point{}.MeasurementTVP.metadata.TVPMeasurementMetadata.qualifier{}.QuantityRange.quality{}.Category.description xml_buffer, point{}.MeasurementTVP.metadata.TVPMeasurementMetadata.qualifier{}.QuantityRange.quality{}.Category.quality{} xml_xml, point{}.MeasurementTVP.metadata.TVPMeasurementMetadata.qualifier{}.QuantityRange.quality{}.Category.quality{}.xlink_href xml_buffer, point{}.MeasurementTVP.metadata.TVPMeasurementMetadata.qualifier{}.QuantityRange.quality{}.Category.quality{}.xlink_title xml_buffer, point{}.MeasurementTVP.metadata.TVPMeasurementMetadata.qualifier{}.QuantityRange.quality{}.Category.nilValues.xlink_href xml_buffer, point{}.MeasurementTVP.metadata.TVPMeasurementMetadata.qualifier{}.QuantityRange.quality{}.Category.nilValues.xlink_title xml_buffer, point{}.MeasurementTVP.metadata.TVPMeasurementMetadata.qualifier{}.QuantityRange.quality{}.Category.nilValues.NilValues.id xml_buffer, point{}.MeasurementTVP.metadata.TVPMeasurementMetadata.qualifier{}.QuantityRange.quality{}.Category.nilValues.NilValues.extension{} xml_xml, point{}.MeasurementTVP.metadata.TVPMeasurementMetadata.qualifier{}.QuantityRange.quality{}.Category.nilValues.NilValues.nilValue{} xml_buffer,
      point{}.MeasurementTVP.metadata.TVPMeasurementMetadata.qualifier{}.QuantityRange.quality{}.Category.nilValues.NilValues.nilValue{}.reason xml_buffer, point{}.MeasurementTVP.metadata.TVPMeasurementMetadata.qualifier{}.QuantityRange.quality{}.Category.codeSpace.xlink_href xml_buffer, point{}.MeasurementTVP.metadata.TVPMeasurementMetadata.qualifier{}.QuantityRange.quality{}.Category.codeSpace.xlink_title xml_buffer, point{}.MeasurementTVP.metadata.TVPMeasurementMetadata.qualifier{}.QuantityRange.quality{}.Category.constraint.xlink_href xml_buffer, point{}.MeasurementTVP.metadata.TVPMeasurementMetadata.qualifier{}.QuantityRange.quality{}.Category.constraint.xlink_title xml_buffer, point{}.MeasurementTVP.metadata.TVPMeasurementMetadata.qualifier{}.QuantityRange.quality{}.Category.constraint.AllowedTokens.id xml_buffer, point{}.MeasurementTVP.metadata.TVPMeasurementMetadata.qualifier{}.QuantityRange.quality{}.Category.constraint.AllowedTokens.extension{} xml_xml, point{}.MeasurementTVP.metadata.TVPMeasurementMetadata.qualifier{}.QuantityRange.quality{}.Category.constraint.AllowedTokens.value{} xml_buffer, point{}.MeasurementTVP.metadata.TVPMeasurementMetadata.qualifier{}.QuantityRange.quality{}.Category.constraint.AllowedTokens.pattern xml_buffer, point{}.MeasurementTVP.metadata.TVPMeasurementMetadata.qualifier{}.QuantityRange.quality{}.Category.value xml_buffer, point{}.MeasurementTVP.metadata.TVPMeasurementMetadata.qualifier{}.QuantityRange.quality{}.Text.referenceFrame xml_buffer, point{}.MeasurementTVP.metadata.TVPMeasurementMetadata.qualifier{}.QuantityRange.quality{}.Text.axisID xml_buffer, point{}.MeasurementTVP.metadata.TVPMeasurementMetadata.qualifier{}.QuantityRange.quality{}.Text.updatable xml_boolean, point{}.MeasurementTVP.metadata.TVPMeasurementMetadata.qualifier{}.QuantityRange.quality{}.Text.optional xml_boolean, point{}.MeasurementTVP.metadata.TVPMeasurementMetadata.qualifier{}.QuantityRange.quality{}.Text.definition xml_buffer, point{}.MeasurementTVP.metadata.TVPMeasurementMetadata.qualifier{}.QuantityRange.quality{}.Text.id xml_buffer, point{}.MeasurementTVP.metadata.TVPMeasurementMetadata.qualifier{}.QuantityRange.quality{}.Text.extension{} xml_xml, point{}.MeasurementTVP.metadata.TVPMeasurementMetadata.qualifier{}.QuantityRange.quality{}.Text.identifier xml_buffer, point{}.MeasurementTVP.metadata.TVPMeasurementMetadata.qualifier{}.QuantityRange.quality{}.Text.label xml_buffer, point{}.MeasurementTVP.metadata.TVPMeasurementMetadata.qualifier{}.QuantityRange.quality{}.Text.description xml_buffer, point{}.MeasurementTVP.metadata.TVPMeasurementMetadata.qualifier{}.QuantityRange.quality{}.Text.quality{} xml_xml, point{}.MeasurementTVP.metadata.TVPMeasurementMetadata.qualifier{}.QuantityRange.quality{}.Text.quality{}.xlink_href xml_buffer, point{}.MeasurementTVP.metadata.TVPMeasurementMetadata.qualifier{}.QuantityRange.quality{}.Text.quality{}.xlink_title xml_buffer, point{}.MeasurementTVP.metadata.TVPMeasurementMetadata.qualifier{}.QuantityRange.quality{}.Text.nilValues.xlink_href xml_buffer, point{}.MeasurementTVP.metadata.TVPMeasurementMetadata.qualifier{}.QuantityRange.quality{}.Text.nilValues.xlink_title xml_buffer, point{}.MeasurementTVP.metadata.TVPMeasurementMetadata.qualifier{}.QuantityRange.quality{}.Text.nilValues.NilValues.id xml_buffer, point{}.MeasurementTVP.metadata.TVPMeasurementMetadata.qualifier{}.QuantityRange.quality{}.Text.nilValues.NilValues.extension{} xml_xml, point{}.MeasurementTVP.metadata.TVPMeasurementMetadata.qualifier{}.QuantityRange.quality{}.Text.nilValues.NilValues.nilValue{} xml_buffer, point{}.MeasurementTVP.metadata.TVPMeasurementMetadata.qualifier{}.QuantityRange.quality{}.Text.nilValues.NilValues.nilValue{}.reason xml_buffer, point{}.MeasurementTVP.metadata.TVPMeasurementMetadata.qualifier{}.QuantityRange.quality{}.Text.constraint.xlink_href xml_buffer,
      point{}.MeasurementTVP.metadata.TVPMeasurementMetadata.qualifier{}.QuantityRange.quality{}.Text.constraint.xlink_title xml_buffer, point{}.MeasurementTVP.metadata.TVPMeasurementMetadata.qualifier{}.QuantityRange.quality{}.Text.constraint.AllowedTokens.id xml_buffer, point{}.MeasurementTVP.metadata.TVPMeasurementMetadata.qualifier{}.QuantityRange.quality{}.Text.constraint.AllowedTokens.extension{} xml_xml, point{}.MeasurementTVP.metadata.TVPMeasurementMetadata.qualifier{}.QuantityRange.quality{}.Text.constraint.AllowedTokens.value{} xml_buffer, point{}.MeasurementTVP.metadata.TVPMeasurementMetadata.qualifier{}.QuantityRange.quality{}.Text.constraint.AllowedTokens.pattern xml_buffer, point{}.MeasurementTVP.metadata.TVPMeasurementMetadata.qualifier{}.QuantityRange.quality{}.Text.value xml_buffer, point{}.MeasurementTVP.metadata.TVPMeasurementMetadata.qualifier{}.QuantityRange.nilValues.xlink_href xml_buffer, point{}.MeasurementTVP.metadata.TVPMeasurementMetadata.qualifier{}.QuantityRange.nilValues.xlink_title xml_buffer, point{}.MeasurementTVP.metadata.TVPMeasurementMetadata.qualifier{}.QuantityRange.nilValues.NilValues.id xml_buffer, point{}.MeasurementTVP.metadata.TVPMeasurementMetadata.qualifier{}.QuantityRange.nilValues.NilValues.extension{} xml_xml, point{}.MeasurementTVP.metadata.TVPMeasurementMetadata.qualifier{}.QuantityRange.nilValues.NilValues.nilValue{} xml_buffer, point{}.MeasurementTVP.metadata.TVPMeasurementMetadata.qualifier{}.QuantityRange.nilValues.NilValues.nilValue{}.reason xml_buffer, point{}.MeasurementTVP.metadata.TVPMeasurementMetadata.qualifier{}.QuantityRange.uom.code xml_buffer, point{}.MeasurementTVP.metadata.TVPMeasurementMetadata.qualifier{}.QuantityRange.uom.xlink_href xml_buffer, point{}.MeasurementTVP.metadata.TVPMeasurementMetadata.qualifier{}.QuantityRange.uom.xlink_title xml_buffer, point{}.MeasurementTVP.metadata.TVPMeasurementMetadata.qualifier{}.QuantityRange.constraint.xlink_href xml_buffer, point{}.MeasurementTVP.metadata.TVPMeasurementMetadata.qualifier{}.QuantityRange.constraint.xlink_title xml_buffer, point{}.MeasurementTVP.metadata.TVPMeasurementMetadata.qualifier{}.QuantityRange.constraint.AllowedValues.id xml_buffer, point{}.MeasurementTVP.metadata.TVPMeasurementMetadata.qualifier{}.QuantityRange.constraint.AllowedValues.extension{} xml_xml, point{}.MeasurementTVP.metadata.TVPMeasurementMetadata.qualifier{}.QuantityRange.constraint.AllowedValues.value{} xml_real64, point{}.MeasurementTVP.metadata.TVPMeasurementMetadata.qualifier{}.QuantityRange.constraint.AllowedValues.interval{} xml_buffer, point{}.MeasurementTVP.metadata.TVPMeasurementMetadata.qualifier{}.QuantityRange.constraint.AllowedValues.significantFigures xml_int64, point{}.MeasurementTVP.metadata.TVPMeasurementMetadata.qualifier{}.QuantityRange.value xml_buffer, point{}.MeasurementTVP.metadata.TVPMeasurementMetadata.qualifier{}.Category.referenceFrame xml_buffer, point{}.MeasurementTVP.metadata.TVPMeasurementMetadata.qualifier{}.Category.axisID xml_buffer, point{}.MeasurementTVP.metadata.TVPMeasurementMetadata.qualifier{}.Category.updatable xml_boolean, point{}.MeasurementTVP.metadata.TVPMeasurementMetadata.qualifier{}.Category.optional xml_boolean, point{}.MeasurementTVP.metadata.TVPMeasurementMetadata.qualifier{}.Category.definition xml_buffer, point{}.MeasurementTVP.metadata.TVPMeasurementMetadata.qualifier{}.Category.id xml_buffer, point{}.MeasurementTVP.metadata.TVPMeasurementMetadata.qualifier{}.Category.extension{} xml_xml,
      point{}.MeasurementTVP.metadata.TVPMeasurementMetadata.qualifier{}.Category.identifier xml_buffer, point{}.MeasurementTVP.metadata.TVPMeasurementMetadata.qualifier{}.Category.label xml_buffer, point{}.MeasurementTVP.metadata.TVPMeasurementMetadata.qualifier{}.Category.description xml_buffer, point{}.MeasurementTVP.metadata.TVPMeasurementMetadata.qualifier{}.Category.quality{}.xlink_href xml_buffer, point{}.MeasurementTVP.metadata.TVPMeasurementMetadata.qualifier{}.Category.quality{}.xlink_title xml_buffer, point{}.MeasurementTVP.metadata.TVPMeasurementMetadata.qualifier{}.Category.quality{}.Quantity.referenceFrame xml_buffer, point{}.MeasurementTVP.metadata.TVPMeasurementMetadata.qualifier{}.Category.quality{}.Quantity.axisID xml_buffer, point{}.MeasurementTVP.metadata.TVPMeasurementMetadata.qualifier{}.Category.quality{}.Quantity.updatable xml_boolean, point{}.MeasurementTVP.metadata.TVPMeasurementMetadata.qualifier{}.Category.quality{}.Quantity.optional xml_boolean, point{}.MeasurementTVP.metadata.TVPMeasurementMetadata.qualifier{}.Category.quality{}.Quantity.definition xml_buffer, point{}.MeasurementTVP.metadata.TVPMeasurementMetadata.qualifier{}.Category.quality{}.Quantity.id xml_buffer, point{}.MeasurementTVP.metadata.TVPMeasurementMetadata.qualifier{}.Category.quality{}.Quantity.extension{} xml_xml, point{}.MeasurementTVP.metadata.TVPMeasurementMetadata.qualifier{}.Category.quality{}.Quantity.identifier xml_buffer, point{}.MeasurementTVP.metadata.TVPMeasurementMetadata.qualifier{}.Category.quality{}.Quantity.label xml_buffer, point{}.MeasurementTVP.metadata.TVPMeasurementMetadata.qualifier{}.Category.quality{}.Quantity.description xml_buffer, point{}.MeasurementTVP.metadata.TVPMeasurementMetadata.qualifier{}.Category.quality{}.Quantity.quality{} xml_xml, point{}.MeasurementTVP.metadata.TVPMeasurementMetadata.qualifier{}.Category.quality{}.Quantity.quality{}.xlink_href xml_buffer, point{}.MeasurementTVP.metadata.TVPMeasurementMetadata.qualifier{}.Category.quality{}.Quantity.quality{}.xlink_title xml_buffer, point{}.MeasurementTVP.metadata.TVPMeasurementMetadata.qualifier{}.Category.quality{}.Quantity.nilValues.xlink_href xml_buffer, point{}.MeasurementTVP.metadata.TVPMeasurementMetadata.qualifier{}.Category.quality{}.Quantity.nilValues.xlink_title xml_buffer, point{}.MeasurementTVP.metadata.TVPMeasurementMetadata.qualifier{}.Category.quality{}.Quantity.nilValues.NilValues.id xml_buffer, point{}.MeasurementTVP.metadata.TVPMeasurementMetadata.qualifier{}.Category.quality{}.Quantity.nilValues.NilValues.extension{} xml_xml, point{}.MeasurementTVP.metadata.TVPMeasurementMetadata.qualifier{}.Category.quality{}.Quantity.nilValues.NilValues.nilValue{} xml_buffer, point{}.MeasurementTVP.metadata.TVPMeasurementMetadata.qualifier{}.Category.quality{}.Quantity.nilValues.NilValues.nilValue{}.reason xml_buffer, point{}.MeasurementTVP.metadata.TVPMeasurementMetadata.qualifier{}.Category.quality{}.Quantity.uom.code xml_buffer, point{}.MeasurementTVP.metadata.TVPMeasurementMetadata.qualifier{}.Category.quality{}.Quantity.uom.xlink_href xml_buffer, point{}.MeasurementTVP.metadata.TVPMeasurementMetadata.qualifier{}.Category.quality{}.Quantity.uom.xlink_title xml_buffer, point{}.MeasurementTVP.metadata.TVPMeasurementMetadata.qualifier{}.Category.quality{}.Quantity.constraint.xlink_href xml_buffer, point{}.MeasurementTVP.metadata.TVPMeasurementMetadata.qualifier{}.Category.quality{}.Quantity.constraint.xlink_title xml_buffer, point{}.MeasurementTVP.metadata.TVPMeasurementMetadata.qualifier{}.Category.quality{}.Quantity.constraint.AllowedValues.id xml_buffer,
      point{}.MeasurementTVP.metadata.TVPMeasurementMetadata.qualifier{}.Category.quality{}.Quantity.constraint.AllowedValues.extension{} xml_xml, point{}.MeasurementTVP.metadata.TVPMeasurementMetadata.qualifier{}.Category.quality{}.Quantity.constraint.AllowedValues.value{} xml_real64, point{}.MeasurementTVP.metadata.TVPMeasurementMetadata.qualifier{}.Category.quality{}.Quantity.constraint.AllowedValues.interval{} xml_buffer, point{}.MeasurementTVP.metadata.TVPMeasurementMetadata.qualifier{}.Category.quality{}.Quantity.constraint.AllowedValues.significantFigures xml_int64, point{}.MeasurementTVP.metadata.TVPMeasurementMetadata.qualifier{}.Category.quality{}.Quantity.value xml_real64, point{}.MeasurementTVP.metadata.TVPMeasurementMetadata.qualifier{}.Category.quality{}.QuantityRange.referenceFrame xml_buffer, point{}.MeasurementTVP.metadata.TVPMeasurementMetadata.qualifier{}.Category.quality{}.QuantityRange.axisID xml_buffer, point{}.MeasurementTVP.metadata.TVPMeasurementMetadata.qualifier{}.Category.quality{}.QuantityRange.updatable xml_boolean, point{}.MeasurementTVP.metadata.TVPMeasurementMetadata.qualifier{}.Category.quality{}.QuantityRange.optional xml_boolean, point{}.MeasurementTVP.metadata.TVPMeasurementMetadata.qualifier{}.Category.quality{}.QuantityRange.definition xml_buffer, point{}.MeasurementTVP.metadata.TVPMeasurementMetadata.qualifier{}.Category.quality{}.QuantityRange.id xml_buffer, point{}.MeasurementTVP.metadata.TVPMeasurementMetadata.qualifier{}.Category.quality{}.QuantityRange.extension{} xml_xml, point{}.MeasurementTVP.metadata.TVPMeasurementMetadata.qualifier{}.Category.quality{}.QuantityRange.identifier xml_buffer, point{}.MeasurementTVP.metadata.TVPMeasurementMetadata.qualifier{}.Category.quality{}.QuantityRange.label xml_buffer, point{}.MeasurementTVP.metadata.TVPMeasurementMetadata.qualifier{}.Category.quality{}.QuantityRange.description xml_buffer, point{}.MeasurementTVP.metadata.TVPMeasurementMetadata.qualifier{}.Category.quality{}.QuantityRange.quality{} xml_xml, point{}.MeasurementTVP.metadata.TVPMeasurementMetadata.qualifier{}.Category.quality{}.QuantityRange.quality{}.xlink_href xml_buffer, point{}.MeasurementTVP.metadata.TVPMeasurementMetadata.qualifier{}.Category.quality{}.QuantityRange.quality{}.xlink_title xml_buffer, point{}.MeasurementTVP.metadata.TVPMeasurementMetadata.qualifier{}.Category.quality{}.QuantityRange.nilValues.xlink_href xml_buffer, point{}.MeasurementTVP.metadata.TVPMeasurementMetadata.qualifier{}.Category.quality{}.QuantityRange.nilValues.xlink_title xml_buffer, point{}.MeasurementTVP.metadata.TVPMeasurementMetadata.qualifier{}.Category.quality{}.QuantityRange.nilValues.NilValues.id xml_buffer, point{}.MeasurementTVP.metadata.TVPMeasurementMetadata.qualifier{}.Category.quality{}.QuantityRange.nilValues.NilValues.extension{} xml_xml, point{}.MeasurementTVP.metadata.TVPMeasurementMetadata.qualifier{}.Category.quality{}.QuantityRange.nilValues.NilValues.nilValue{} xml_buffer, point{}.MeasurementTVP.metadata.TVPMeasurementMetadata.qualifier{}.Category.quality{}.QuantityRange.nilValues.NilValues.nilValue{}.reason xml_buffer, point{}.MeasurementTVP.metadata.TVPMeasurementMetadata.qualifier{}.Category.quality{}.QuantityRange.uom.code xml_buffer, point{}.MeasurementTVP.metadata.TVPMeasurementMetadata.qualifier{}.Category.quality{}.QuantityRange.uom.xlink_href xml_buffer, point{}.MeasurementTVP.metadata.TVPMeasurementMetadata.qualifier{}.Category.quality{}.QuantityRange.uom.xlink_title xml_buffer, point{}.MeasurementTVP.metadata.TVPMeasurementMetadata.qualifier{}.Category.quality{}.QuantityRange.constraint.xlink_href xml_buffer, point{}.MeasurementTVP.metadata.TVPMeasurementMetadata.qualifier{}.Category.quality{}.QuantityRange.constraint.xlink_title xml_buffer, point{}.MeasurementTVP.metadata.TVPMeasurementMetadata.qualifier{}.Category.quality{}.QuantityRange.constraint.AllowedValues.id xml_buffer,
      point{}.MeasurementTVP.metadata.TVPMeasurementMetadata.qualifier{}.Category.quality{}.QuantityRange.constraint.AllowedValues.extension{} xml_xml, point{}.MeasurementTVP.metadata.TVPMeasurementMetadata.qualifier{}.Category.quality{}.QuantityRange.constraint.AllowedValues.value{} xml_real64, point{}.MeasurementTVP.metadata.TVPMeasurementMetadata.qualifier{}.Category.quality{}.QuantityRange.constraint.AllowedValues.interval{} xml_buffer, point{}.MeasurementTVP.metadata.TVPMeasurementMetadata.qualifier{}.Category.quality{}.QuantityRange.constraint.AllowedValues.significantFigures xml_int64, point{}.MeasurementTVP.metadata.TVPMeasurementMetadata.qualifier{}.Category.quality{}.QuantityRange.value xml_buffer, point{}.MeasurementTVP.metadata.TVPMeasurementMetadata.qualifier{}.Category.quality{}.Category xml_xml, point{}.MeasurementTVP.metadata.TVPMeasurementMetadata.qualifier{}.Category.quality{}.Category.referenceFrame xml_buffer, point{}.MeasurementTVP.metadata.TVPMeasurementMetadata.qualifier{}.Category.quality{}.Category.axisID xml_buffer, point{}.MeasurementTVP.metadata.TVPMeasurementMetadata.qualifier{}.Category.quality{}.Category.updatable xml_boolean, point{}.MeasurementTVP.metadata.TVPMeasurementMetadata.qualifier{}.Category.quality{}.Category.optional xml_boolean, point{}.MeasurementTVP.metadata.TVPMeasurementMetadata.qualifier{}.Category.quality{}.Category.definition xml_buffer, point{}.MeasurementTVP.metadata.TVPMeasurementMetadata.qualifier{}.Category.quality{}.Category.id xml_buffer, point{}.MeasurementTVP.metadata.TVPMeasurementMetadata.qualifier{}.Category.quality{}.Text.referenceFrame xml_buffer, point{}.MeasurementTVP.metadata.TVPMeasurementMetadata.qualifier{}.Category.quality{}.Text.axisID xml_buffer, point{}.MeasurementTVP.metadata.TVPMeasurementMetadata.qualifier{}.Category.quality{}.Text.updatable xml_boolean, point{}.MeasurementTVP.metadata.TVPMeasurementMetadata.qualifier{}.Category.quality{}.Text.optional xml_boolean, point{}.MeasurementTVP.metadata.TVPMeasurementMetadata.qualifier{}.Category.quality{}.Text.definition xml_buffer, point{}.MeasurementTVP.metadata.TVPMeasurementMetadata.qualifier{}.Category.quality{}.Text.id xml_buffer, point{}.MeasurementTVP.metadata.TVPMeasurementMetadata.qualifier{}.Category.quality{}.Text.extension{} xml_xml, point{}.MeasurementTVP.metadata.TVPMeasurementMetadata.qualifier{}.Category.quality{}.Text.identifier xml_buffer, point{}.MeasurementTVP.metadata.TVPMeasurementMetadata.qualifier{}.Category.quality{}.Text.label xml_buffer, point{}.MeasurementTVP.metadata.TVPMeasurementMetadata.qualifier{}.Category.quality{}.Text.description xml_buffer, point{}.MeasurementTVP.metadata.TVPMeasurementMetadata.qualifier{}.Category.quality{}.Text.quality{} xml_xml, point{}.MeasurementTVP.metadata.TVPMeasurementMetadata.qualifier{}.Category.quality{}.Text.quality{}.xlink_href xml_buffer, point{}.MeasurementTVP.metadata.TVPMeasurementMetadata.qualifier{}.Category.quality{}.Text.quality{}.xlink_title xml_buffer, point{}.MeasurementTVP.metadata.TVPMeasurementMetadata.qualifier{}.Category.quality{}.Text.nilValues.xlink_href xml_buffer, point{}.MeasurementTVP.metadata.TVPMeasurementMetadata.qualifier{}.Category.quality{}.Text.nilValues.xlink_title xml_buffer, point{}.MeasurementTVP.metadata.TVPMeasurementMetadata.qualifier{}.Category.quality{}.Text.nilValues.NilValues.id xml_buffer, point{}.MeasurementTVP.metadata.TVPMeasurementMetadata.qualifier{}.Category.quality{}.Text.nilValues.NilValues.extension{} xml_xml, point{}.MeasurementTVP.metadata.TVPMeasurementMetadata.qualifier{}.Category.quality{}.Text.nilValues.NilValues.nilValue{} xml_buffer,
      point{}.MeasurementTVP.metadata.TVPMeasurementMetadata.qualifier{}.Category.quality{}.Text.nilValues.NilValues.nilValue{}.reason xml_buffer, point{}.MeasurementTVP.metadata.TVPMeasurementMetadata.qualifier{}.Category.quality{}.Text.constraint.xlink_href xml_buffer, point{}.MeasurementTVP.metadata.TVPMeasurementMetadata.qualifier{}.Category.quality{}.Text.constraint.xlink_title xml_buffer, point{}.MeasurementTVP.metadata.TVPMeasurementMetadata.qualifier{}.Category.quality{}.Text.constraint.AllowedTokens.id xml_buffer, point{}.MeasurementTVP.metadata.TVPMeasurementMetadata.qualifier{}.Category.quality{}.Text.constraint.AllowedTokens.extension{} xml_xml, point{}.MeasurementTVP.metadata.TVPMeasurementMetadata.qualifier{}.Category.quality{}.Text.constraint.AllowedTokens.value{} xml_buffer, point{}.MeasurementTVP.metadata.TVPMeasurementMetadata.qualifier{}.Category.quality{}.Text.constraint.AllowedTokens.pattern xml_buffer, point{}.MeasurementTVP.metadata.TVPMeasurementMetadata.qualifier{}.Category.quality{}.Text.value xml_buffer, point{}.MeasurementTVP.metadata.TVPMeasurementMetadata.qualifier{}.Category.nilValues.xlink_href xml_buffer, point{}.MeasurementTVP.metadata.TVPMeasurementMetadata.qualifier{}.Category.nilValues.xlink_title xml_buffer, point{}.MeasurementTVP.metadata.TVPMeasurementMetadata.qualifier{}.Category.nilValues.NilValues.id xml_buffer, point{}.MeasurementTVP.metadata.TVPMeasurementMetadata.qualifier{}.Category.nilValues.NilValues.extension{} xml_xml, point{}.MeasurementTVP.metadata.TVPMeasurementMetadata.qualifier{}.Category.nilValues.NilValues.nilValue{} xml_buffer, point{}.MeasurementTVP.metadata.TVPMeasurementMetadata.qualifier{}.Category.nilValues.NilValues.nilValue{}.reason xml_buffer, point{}.MeasurementTVP.metadata.TVPMeasurementMetadata.qualifier{}.Category.codeSpace.xlink_href xml_buffer, point{}.MeasurementTVP.metadata.TVPMeasurementMetadata.qualifier{}.Category.codeSpace.xlink_title xml_buffer, point{}.MeasurementTVP.metadata.TVPMeasurementMetadata.qualifier{}.Category.constraint.xlink_href xml_buffer, point{}.MeasurementTVP.metadata.TVPMeasurementMetadata.qualifier{}.Category.constraint.xlink_title xml_buffer, point{}.MeasurementTVP.metadata.TVPMeasurementMetadata.qualifier{}.Category.constraint.AllowedTokens.id xml_buffer, point{}.MeasurementTVP.metadata.TVPMeasurementMetadata.qualifier{}.Category.constraint.AllowedTokens.extension{} xml_xml, point{}.MeasurementTVP.metadata.TVPMeasurementMetadata.qualifier{}.Category.constraint.AllowedTokens.value{} xml_buffer, point{}.MeasurementTVP.metadata.TVPMeasurementMetadata.qualifier{}.Category.constraint.AllowedTokens.pattern xml_buffer, point{}.MeasurementTVP.metadata.TVPMeasurementMetadata.qualifier{}.Category.value xml_buffer, point{}.MeasurementTVP.metadata.TVPMeasurementMetadata.qualifier{}.Text.referenceFrame xml_buffer, point{}.MeasurementTVP.metadata.TVPMeasurementMetadata.qualifier{}.Text.axisID xml_buffer, point{}.MeasurementTVP.metadata.TVPMeasurementMetadata.qualifier{}.Text.updatable xml_boolean, point{}.MeasurementTVP.metadata.TVPMeasurementMetadata.qualifier{}.Text.optional xml_boolean, point{}.MeasurementTVP.metadata.TVPMeasurementMetadata.qualifier{}.Text.definition xml_buffer, point{}.MeasurementTVP.metadata.TVPMeasurementMetadata.qualifier{}.Text.id xml_buffer, point{}.MeasurementTVP.metadata.TVPMeasurementMetadata.qualifier{}.Text.extension{} xml_xml,
      point{}.MeasurementTVP.metadata.TVPMeasurementMetadata.qualifier{}.Text.identifier xml_buffer, point{}.MeasurementTVP.metadata.TVPMeasurementMetadata.qualifier{}.Text.label xml_buffer, point{}.MeasurementTVP.metadata.TVPMeasurementMetadata.qualifier{}.Text.description xml_buffer, point{}.MeasurementTVP.metadata.TVPMeasurementMetadata.qualifier{}.Text.quality{}.xlink_href xml_buffer, point{}.MeasurementTVP.metadata.TVPMeasurementMetadata.qualifier{}.Text.quality{}.xlink_title xml_buffer, point{}.MeasurementTVP.metadata.TVPMeasurementMetadata.qualifier{}.Text.quality{}.Quantity.referenceFrame xml_buffer, point{}.MeasurementTVP.metadata.TVPMeasurementMetadata.qualifier{}.Text.quality{}.Quantity.axisID xml_buffer, point{}.MeasurementTVP.metadata.TVPMeasurementMetadata.qualifier{}.Text.quality{}.Quantity.updatable xml_boolean, point{}.MeasurementTVP.metadata.TVPMeasurementMetadata.qualifier{}.Text.quality{}.Quantity.optional xml_boolean, point{}.MeasurementTVP.metadata.TVPMeasurementMetadata.qualifier{}.Text.quality{}.Quantity.definition xml_buffer, point{}.MeasurementTVP.metadata.TVPMeasurementMetadata.qualifier{}.Text.quality{}.Quantity.id xml_buffer, point{}.MeasurementTVP.metadata.TVPMeasurementMetadata.qualifier{}.Text.quality{}.Quantity.extension{} xml_xml, point{}.MeasurementTVP.metadata.TVPMeasurementMetadata.qualifier{}.Text.quality{}.Quantity.identifier xml_buffer, point{}.MeasurementTVP.metadata.TVPMeasurementMetadata.qualifier{}.Text.quality{}.Quantity.label xml_buffer, point{}.MeasurementTVP.metadata.TVPMeasurementMetadata.qualifier{}.Text.quality{}.Quantity.description xml_buffer, point{}.MeasurementTVP.metadata.TVPMeasurementMetadata.qualifier{}.Text.quality{}.Quantity.quality{} xml_xml, point{}.MeasurementTVP.metadata.TVPMeasurementMetadata.qualifier{}.Text.quality{}.Quantity.quality{}.xlink_href xml_buffer, point{}.MeasurementTVP.metadata.TVPMeasurementMetadata.qualifier{}.Text.quality{}.Quantity.quality{}.xlink_title xml_buffer, point{}.MeasurementTVP.metadata.TVPMeasurementMetadata.qualifier{}.Text.quality{}.Quantity.nilValues.xlink_href xml_buffer, point{}.MeasurementTVP.metadata.TVPMeasurementMetadata.qualifier{}.Text.quality{}.Quantity.nilValues.xlink_title xml_buffer, point{}.MeasurementTVP.metadata.TVPMeasurementMetadata.qualifier{}.Text.quality{}.Quantity.nilValues.NilValues.id xml_buffer, point{}.MeasurementTVP.metadata.TVPMeasurementMetadata.qualifier{}.Text.quality{}.Quantity.nilValues.NilValues.extension{} xml_xml, point{}.MeasurementTVP.metadata.TVPMeasurementMetadata.qualifier{}.Text.quality{}.Quantity.nilValues.NilValues.nilValue{} xml_buffer, point{}.MeasurementTVP.metadata.TVPMeasurementMetadata.qualifier{}.Text.quality{}.Quantity.nilValues.NilValues.nilValue{}.reason xml_buffer, point{}.MeasurementTVP.metadata.TVPMeasurementMetadata.qualifier{}.Text.quality{}.Quantity.uom.code xml_buffer, point{}.MeasurementTVP.metadata.TVPMeasurementMetadata.qualifier{}.Text.quality{}.Quantity.uom.xlink_href xml_buffer, point{}.MeasurementTVP.metadata.TVPMeasurementMetadata.qualifier{}.Text.quality{}.Quantity.uom.xlink_title xml_buffer, point{}.MeasurementTVP.metadata.TVPMeasurementMetadata.qualifier{}.Text.quality{}.Quantity.constraint.xlink_href xml_buffer, point{}.MeasurementTVP.metadata.TVPMeasurementMetadata.qualifier{}.Text.quality{}.Quantity.constraint.xlink_title xml_buffer, point{}.MeasurementTVP.metadata.TVPMeasurementMetadata.qualifier{}.Text.quality{}.Quantity.constraint.AllowedValues.id xml_buffer,
      point{}.MeasurementTVP.metadata.TVPMeasurementMetadata.qualifier{}.Text.quality{}.Quantity.constraint.AllowedValues.extension{} xml_xml, point{}.MeasurementTVP.metadata.TVPMeasurementMetadata.qualifier{}.Text.quality{}.Quantity.constraint.AllowedValues.value{} xml_real64, point{}.MeasurementTVP.metadata.TVPMeasurementMetadata.qualifier{}.Text.quality{}.Quantity.constraint.AllowedValues.interval{} xml_buffer, point{}.MeasurementTVP.metadata.TVPMeasurementMetadata.qualifier{}.Text.quality{}.Quantity.constraint.AllowedValues.significantFigures xml_int64, point{}.MeasurementTVP.metadata.TVPMeasurementMetadata.qualifier{}.Text.quality{}.Quantity.value xml_real64, point{}.MeasurementTVP.metadata.TVPMeasurementMetadata.qualifier{}.Text.quality{}.QuantityRange.referenceFrame xml_buffer, point{}.MeasurementTVP.metadata.TVPMeasurementMetadata.qualifier{}.Text.quality{}.QuantityRange.axisID xml_buffer, point{}.MeasurementTVP.metadata.TVPMeasurementMetadata.qualifier{}.Text.quality{}.QuantityRange.updatable xml_boolean, point{}.MeasurementTVP.metadata.TVPMeasurementMetadata.qualifier{}.Text.quality{}.QuantityRange.optional xml_boolean, point{}.MeasurementTVP.metadata.TVPMeasurementMetadata.qualifier{}.Text.quality{}.QuantityRange.definition xml_buffer, point{}.MeasurementTVP.metadata.TVPMeasurementMetadata.qualifier{}.Text.quality{}.QuantityRange.id xml_buffer, point{}.MeasurementTVP.metadata.TVPMeasurementMetadata.qualifier{}.Text.quality{}.QuantityRange.extension{} xml_xml, point{}.MeasurementTVP.metadata.TVPMeasurementMetadata.qualifier{}.Text.quality{}.QuantityRange.identifier xml_buffer, point{}.MeasurementTVP.metadata.TVPMeasurementMetadata.qualifier{}.Text.quality{}.QuantityRange.label xml_buffer, point{}.MeasurementTVP.metadata.TVPMeasurementMetadata.qualifier{}.Text.quality{}.QuantityRange.description xml_buffer, point{}.MeasurementTVP.metadata.TVPMeasurementMetadata.qualifier{}.Text.quality{}.QuantityRange.quality{} xml_xml, point{}.MeasurementTVP.metadata.TVPMeasurementMetadata.qualifier{}.Text.quality{}.QuantityRange.quality{}.xlink_href xml_buffer, point{}.MeasurementTVP.metadata.TVPMeasurementMetadata.qualifier{}.Text.quality{}.QuantityRange.quality{}.xlink_title xml_buffer, point{}.MeasurementTVP.metadata.TVPMeasurementMetadata.qualifier{}.Text.quality{}.QuantityRange.nilValues.xlink_href xml_buffer, point{}.MeasurementTVP.metadata.TVPMeasurementMetadata.qualifier{}.Text.quality{}.QuantityRange.nilValues.xlink_title xml_buffer, point{}.MeasurementTVP.metadata.TVPMeasurementMetadata.qualifier{}.Text.quality{}.QuantityRange.nilValues.NilValues.id xml_buffer, point{}.MeasurementTVP.metadata.TVPMeasurementMetadata.qualifier{}.Text.quality{}.QuantityRange.nilValues.NilValues.extension{} xml_xml, point{}.MeasurementTVP.metadata.TVPMeasurementMetadata.qualifier{}.Text.quality{}.QuantityRange.nilValues.NilValues.nilValue{} xml_buffer, point{}.MeasurementTVP.metadata.TVPMeasurementMetadata.qualifier{}.Text.quality{}.QuantityRange.nilValues.NilValues.nilValue{}.reason xml_buffer, point{}.MeasurementTVP.metadata.TVPMeasurementMetadata.qualifier{}.Text.quality{}.QuantityRange.uom.code xml_buffer, point{}.MeasurementTVP.metadata.TVPMeasurementMetadata.qualifier{}.Text.quality{}.QuantityRange.uom.xlink_href xml_buffer, point{}.MeasurementTVP.metadata.TVPMeasurementMetadata.qualifier{}.Text.quality{}.QuantityRange.uom.xlink_title xml_buffer, point{}.MeasurementTVP.metadata.TVPMeasurementMetadata.qualifier{}.Text.quality{}.QuantityRange.constraint.xlink_href xml_buffer, point{}.MeasurementTVP.metadata.TVPMeasurementMetadata.qualifier{}.Text.quality{}.QuantityRange.constraint.xlink_title xml_buffer, point{}.MeasurementTVP.metadata.TVPMeasurementMetadata.qualifier{}.Text.quality{}.QuantityRange.constraint.AllowedValues.id xml_buffer,
      point{}.MeasurementTVP.metadata.TVPMeasurementMetadata.qualifier{}.Text.quality{}.QuantityRange.constraint.AllowedValues.extension{} xml_xml, point{}.MeasurementTVP.metadata.TVPMeasurementMetadata.qualifier{}.Text.quality{}.QuantityRange.constraint.AllowedValues.value{} xml_real64, point{}.MeasurementTVP.metadata.TVPMeasurementMetadata.qualifier{}.Text.quality{}.QuantityRange.constraint.AllowedValues.interval{} xml_buffer, point{}.MeasurementTVP.metadata.TVPMeasurementMetadata.qualifier{}.Text.quality{}.QuantityRange.constraint.AllowedValues.significantFigures xml_int64, point{}.MeasurementTVP.metadata.TVPMeasurementMetadata.qualifier{}.Text.quality{}.QuantityRange.value xml_buffer, point{}.MeasurementTVP.metadata.TVPMeasurementMetadata.qualifier{}.Text.quality{}.Category.referenceFrame xml_buffer, point{}.MeasurementTVP.metadata.TVPMeasurementMetadata.qualifier{}.Text.quality{}.Category.axisID xml_buffer, point{}.MeasurementTVP.metadata.TVPMeasurementMetadata.qualifier{}.Text.quality{}.Category.updatable xml_boolean, point{}.MeasurementTVP.metadata.TVPMeasurementMetadata.qualifier{}.Text.quality{}.Category.optional xml_boolean, point{}.MeasurementTVP.metadata.TVPMeasurementMetadata.qualifier{}.Text.quality{}.Category.definition xml_buffer, point{}.MeasurementTVP.metadata.TVPMeasurementMetadata.qualifier{}.Text.quality{}.Category.id xml_buffer, point{}.MeasurementTVP.metadata.TVPMeasurementMetadata.qualifier{}.Text.quality{}.Category.extension{} xml_xml, point{}.MeasurementTVP.metadata.TVPMeasurementMetadata.qualifier{}.Text.quality{}.Category.identifier xml_buffer, point{}.MeasurementTVP.metadata.TVPMeasurementMetadata.qualifier{}.Text.quality{}.Category.label xml_buffer, point{}.MeasurementTVP.metadata.TVPMeasurementMetadata.qualifier{}.Text.quality{}.Category.description xml_buffer, point{}.MeasurementTVP.metadata.TVPMeasurementMetadata.qualifier{}.Text.quality{}.Category.quality{} xml_xml, point{}.MeasurementTVP.metadata.TVPMeasurementMetadata.qualifier{}.Text.quality{}.Category.quality{}.xlink_href xml_buffer, point{}.MeasurementTVP.metadata.TVPMeasurementMetadata.qualifier{}.Text.quality{}.Category.quality{}.xlink_title xml_buffer, point{}.MeasurementTVP.metadata.TVPMeasurementMetadata.qualifier{}.Text.quality{}.Category.nilValues.xlink_href xml_buffer, point{}.MeasurementTVP.metadata.TVPMeasurementMetadata.qualifier{}.Text.quality{}.Category.nilValues.xlink_title xml_buffer, point{}.MeasurementTVP.metadata.TVPMeasurementMetadata.qualifier{}.Text.quality{}.Category.nilValues.NilValues.id xml_buffer, point{}.MeasurementTVP.metadata.TVPMeasurementMetadata.qualifier{}.Text.quality{}.Category.nilValues.NilValues.extension{} xml_xml, point{}.MeasurementTVP.metadata.TVPMeasurementMetadata.qualifier{}.Text.quality{}.Category.nilValues.NilValues.nilValue{} xml_buffer, point{}.MeasurementTVP.metadata.TVPMeasurementMetadata.qualifier{}.Text.quality{}.Category.nilValues.NilValues.nilValue{}.reason xml_buffer, point{}.MeasurementTVP.metadata.TVPMeasurementMetadata.qualifier{}.Text.quality{}.Category.codeSpace.xlink_href xml_buffer, point{}.MeasurementTVP.metadata.TVPMeasurementMetadata.qualifier{}.Text.quality{}.Category.codeSpace.xlink_title xml_buffer, point{}.MeasurementTVP.metadata.TVPMeasurementMetadata.qualifier{}.Text.quality{}.Category.constraint.xlink_href xml_buffer, point{}.MeasurementTVP.metadata.TVPMeasurementMetadata.qualifier{}.Text.quality{}.Category.constraint.xlink_title xml_buffer, point{}.MeasurementTVP.metadata.TVPMeasurementMetadata.qualifier{}.Text.quality{}.Category.constraint.AllowedTokens.id xml_buffer, point{}.MeasurementTVP.metadata.TVPMeasurementMetadata.qualifier{}.Text.quality{}.Category.constraint.AllowedTokens.extension{} xml_xml,
      point{}.MeasurementTVP.metadata.TVPMeasurementMetadata.qualifier{}.Text.quality{}.Category.constraint.AllowedTokens.value{} xml_buffer, point{}.MeasurementTVP.metadata.TVPMeasurementMetadata.qualifier{}.Text.quality{}.Category.constraint.AllowedTokens.pattern xml_buffer, point{}.MeasurementTVP.metadata.TVPMeasurementMetadata.qualifier{}.Text.quality{}.Category.value xml_buffer, point{}.MeasurementTVP.metadata.TVPMeasurementMetadata.qualifier{}.Text.quality{}.Text xml_xml, point{}.MeasurementTVP.metadata.TVPMeasurementMetadata.qualifier{}.Text.quality{}.Text.referenceFrame xml_buffer, point{}.MeasurementTVP.metadata.TVPMeasurementMetadata.qualifier{}.Text.quality{}.Text.axisID xml_buffer, point{}.MeasurementTVP.metadata.TVPMeasurementMetadata.qualifier{}.Text.quality{}.Text.updatable xml_boolean, point{}.MeasurementTVP.metadata.TVPMeasurementMetadata.qualifier{}.Text.quality{}.Text.optional xml_boolean, point{}.MeasurementTVP.metadata.TVPMeasurementMetadata.qualifier{}.Text.quality{}.Text.definition xml_buffer, point{}.MeasurementTVP.metadata.TVPMeasurementMetadata.qualifier{}.Text.quality{}.Text.id xml_buffer, point{}.MeasurementTVP.metadata.TVPMeasurementMetadata.qualifier{}.Text.nilValues.xlink_href xml_buffer, point{}.MeasurementTVP.metadata.TVPMeasurementMetadata.qualifier{}.Text.nilValues.xlink_title xml_buffer, point{}.MeasurementTVP.metadata.TVPMeasurementMetadata.qualifier{}.Text.nilValues.NilValues.id xml_buffer, point{}.MeasurementTVP.metadata.TVPMeasurementMetadata.qualifier{}.Text.nilValues.NilValues.extension{} xml_xml, point{}.MeasurementTVP.metadata.TVPMeasurementMetadata.qualifier{}.Text.nilValues.NilValues.nilValue{} xml_buffer, point{}.MeasurementTVP.metadata.TVPMeasurementMetadata.qualifier{}.Text.nilValues.NilValues.nilValue{}.reason xml_buffer, point{}.MeasurementTVP.metadata.TVPMeasurementMetadata.qualifier{}.Text.constraint.xlink_href xml_buffer, point{}.MeasurementTVP.metadata.TVPMeasurementMetadata.qualifier{}.Text.constraint.xlink_title xml_buffer, point{}.MeasurementTVP.metadata.TVPMeasurementMetadata.qualifier{}.Text.constraint.AllowedTokens.id xml_buffer, point{}.MeasurementTVP.metadata.TVPMeasurementMetadata.qualifier{}.Text.constraint.AllowedTokens.extension{} xml_xml, point{}.MeasurementTVP.metadata.TVPMeasurementMetadata.qualifier{}.Text.constraint.AllowedTokens.value{} xml_buffer, point{}.MeasurementTVP.metadata.TVPMeasurementMetadata.qualifier{}.Text.constraint.AllowedTokens.pattern xml_buffer, point{}.MeasurementTVP.metadata.TVPMeasurementMetadata.qualifier{}.Text.value xml_buffer, point{}.MeasurementTVP.metadata.TVPMeasurementMetadata.processing.owns xml_boolean, point{}.MeasurementTVP.metadata.TVPMeasurementMetadata.processing.nilReason xml_buffer, point{}.MeasurementTVP.metadata.TVPMeasurementMetadata.processing.gml_remoteSchema xml_buffer, point{}.MeasurementTVP.metadata.TVPMeasurementMetadata.processing.xlink_href xml_buffer, point{}.MeasurementTVP.metadata.TVPMeasurementMetadata.processing.xlink_title xml_buffer, point{}.MeasurementTVP.metadata.TVPMeasurementMetadata.source.owns xml_boolean, point{}.MeasurementTVP.metadata.TVPMeasurementMetadata.source.nilReason xml_buffer,
      point{}.MeasurementTVP.metadata.TVPMeasurementMetadata.source.gml_remoteSchema xml_buffer, point{}.MeasurementTVP.metadata.TVPMeasurementMetadata.source.xlink_href xml_buffer, point{}.MeasurementTVP.metadata.TVPMeasurementMetadata.source.xlink_title xml_buffer, point{}.MeasurementTVP.metadata.TVPMeasurementMetadata.uom.code xml_buffer, point{}.MeasurementTVP.metadata.TVPMeasurementMetadata.uom.xlink_href xml_buffer, point{}.MeasurementTVP.metadata.TVPMeasurementMetadata.uom.xlink_title xml_buffer, point{}.MeasurementTVP.metadata.TVPMeasurementMetadata.interpolationType.owns xml_boolean, point{}.MeasurementTVP.metadata.TVPMeasurementMetadata.interpolationType.nilReason xml_buffer, point{}.MeasurementTVP.metadata.TVPMeasurementMetadata.interpolationType.gml_remoteSchema xml_buffer, point{}.MeasurementTVP.metadata.TVPMeasurementMetadata.interpolationType.xlink_href xml_buffer, point{}.MeasurementTVP.metadata.TVPMeasurementMetadata.interpolationType.xlink_title xml_buffer, point{}.MeasurementTVP.metadata.TVPMeasurementMetadata.censoredReason.owns xml_boolean, point{}.MeasurementTVP.metadata.TVPMeasurementMetadata.censoredReason.nilReason xml_buffer, point{}.MeasurementTVP.metadata.TVPMeasurementMetadata.censoredReason.gml_remoteSchema xml_buffer, point{}.MeasurementTVP.metadata.TVPMeasurementMetadata.censoredReason.xlink_href xml_buffer, point{}.MeasurementTVP.metadata.TVPMeasurementMetadata.censoredReason.xlink_title xml_buffer, point{}.MeasurementTVP.metadata.TVPMeasurementMetadata.accuracy.xlink_href xml_buffer, point{}.MeasurementTVP.metadata.TVPMeasurementMetadata.accuracy.xlink_title xml_buffer, point{}.MeasurementTVP.metadata.TVPMeasurementMetadata.accuracy.Quantity.referenceFrame xml_buffer, point{}.MeasurementTVP.metadata.TVPMeasurementMetadata.accuracy.Quantity.axisID xml_buffer, point{}.MeasurementTVP.metadata.TVPMeasurementMetadata.accuracy.Quantity.updatable xml_boolean, point{}.MeasurementTVP.metadata.TVPMeasurementMetadata.accuracy.Quantity.optional xml_boolean, point{}.MeasurementTVP.metadata.TVPMeasurementMetadata.accuracy.Quantity.definition xml_buffer, point{}.MeasurementTVP.metadata.TVPMeasurementMetadata.accuracy.Quantity.id xml_buffer, point{}.MeasurementTVP.metadata.TVPMeasurementMetadata.accuracy.Quantity.extension{} xml_xml, point{}.MeasurementTVP.metadata.TVPMeasurementMetadata.accuracy.Quantity.identifier xml_buffer, point{}.MeasurementTVP.metadata.TVPMeasurementMetadata.accuracy.Quantity.label xml_buffer, point{}.MeasurementTVP.metadata.TVPMeasurementMetadata.accuracy.Quantity.description xml_buffer, point{}.MeasurementTVP.metadata.TVPMeasurementMetadata.accuracy.Quantity.quality{}.xlink_href xml_buffer, point{}.MeasurementTVP.metadata.TVPMeasurementMetadata.accuracy.Quantity.quality{}.xlink_title xml_buffer,
      point{}.MeasurementTVP.metadata.TVPMeasurementMetadata.accuracy.Quantity.quality{}.Quantity xml_xml, point{}.MeasurementTVP.metadata.TVPMeasurementMetadata.accuracy.Quantity.quality{}.Quantity.referenceFrame xml_buffer, point{}.MeasurementTVP.metadata.TVPMeasurementMetadata.accuracy.Quantity.quality{}.Quantity.axisID xml_buffer, point{}.MeasurementTVP.metadata.TVPMeasurementMetadata.accuracy.Quantity.quality{}.Quantity.updatable xml_boolean, point{}.MeasurementTVP.metadata.TVPMeasurementMetadata.accuracy.Quantity.quality{}.Quantity.optional xml_boolean, point{}.MeasurementTVP.metadata.TVPMeasurementMetadata.accuracy.Quantity.quality{}.Quantity.definition xml_buffer, point{}.MeasurementTVP.metadata.TVPMeasurementMetadata.accuracy.Quantity.quality{}.Quantity.id xml_buffer, point{}.MeasurementTVP.metadata.TVPMeasurementMetadata.accuracy.Quantity.quality{}.QuantityRange.referenceFrame xml_buffer, point{}.MeasurementTVP.metadata.TVPMeasurementMetadata.accuracy.Quantity.quality{}.QuantityRange.axisID xml_buffer, point{}.MeasurementTVP.metadata.TVPMeasurementMetadata.accuracy.Quantity.quality{}.QuantityRange.updatable xml_boolean, point{}.MeasurementTVP.metadata.TVPMeasurementMetadata.accuracy.Quantity.quality{}.QuantityRange.optional xml_boolean, point{}.MeasurementTVP.metadata.TVPMeasurementMetadata.accuracy.Quantity.quality{}.QuantityRange.definition xml_buffer, point{}.MeasurementTVP.metadata.TVPMeasurementMetadata.accuracy.Quantity.quality{}.QuantityRange.id xml_buffer, point{}.MeasurementTVP.metadata.TVPMeasurementMetadata.accuracy.Quantity.quality{}.QuantityRange.extension{} xml_xml, point{}.MeasurementTVP.metadata.TVPMeasurementMetadata.accuracy.Quantity.quality{}.QuantityRange.identifier xml_buffer, point{}.MeasurementTVP.metadata.TVPMeasurementMetadata.accuracy.Quantity.quality{}.QuantityRange.label xml_buffer, point{}.MeasurementTVP.metadata.TVPMeasurementMetadata.accuracy.Quantity.quality{}.QuantityRange.description xml_buffer, point{}.MeasurementTVP.metadata.TVPMeasurementMetadata.accuracy.Quantity.quality{}.QuantityRange.quality{} xml_xml, point{}.MeasurementTVP.metadata.TVPMeasurementMetadata.accuracy.Quantity.quality{}.QuantityRange.quality{}.xlink_href xml_buffer, point{}.MeasurementTVP.metadata.TVPMeasurementMetadata.accuracy.Quantity.quality{}.QuantityRange.quality{}.xlink_title xml_buffer, point{}.MeasurementTVP.metadata.TVPMeasurementMetadata.accuracy.Quantity.quality{}.QuantityRange.nilValues.xlink_href xml_buffer, point{}.MeasurementTVP.metadata.TVPMeasurementMetadata.accuracy.Quantity.quality{}.QuantityRange.nilValues.xlink_title xml_buffer, point{}.MeasurementTVP.metadata.TVPMeasurementMetadata.accuracy.Quantity.quality{}.QuantityRange.nilValues.NilValues.id xml_buffer, point{}.MeasurementTVP.metadata.TVPMeasurementMetadata.accuracy.Quantity.quality{}.QuantityRange.nilValues.NilValues.extension{} xml_xml, point{}.MeasurementTVP.metadata.TVPMeasurementMetadata.accuracy.Quantity.quality{}.QuantityRange.nilValues.NilValues.nilValue{} xml_buffer, point{}.MeasurementTVP.metadata.TVPMeasurementMetadata.accuracy.Quantity.quality{}.QuantityRange.nilValues.NilValues.nilValue{}.reason xml_buffer, point{}.MeasurementTVP.metadata.TVPMeasurementMetadata.accuracy.Quantity.quality{}.QuantityRange.uom.code xml_buffer, point{}.MeasurementTVP.metadata.TVPMeasurementMetadata.accuracy.Quantity.quality{}.QuantityRange.uom.xlink_href xml_buffer, point{}.MeasurementTVP.metadata.TVPMeasurementMetadata.accuracy.Quantity.quality{}.QuantityRange.uom.xlink_title xml_buffer, point{}.MeasurementTVP.metadata.TVPMeasurementMetadata.accuracy.Quantity.quality{}.QuantityRange.constraint.xlink_href xml_buffer,
      point{}.MeasurementTVP.metadata.TVPMeasurementMetadata.accuracy.Quantity.quality{}.QuantityRange.constraint.xlink_title xml_buffer, point{}.MeasurementTVP.metadata.TVPMeasurementMetadata.accuracy.Quantity.quality{}.QuantityRange.constraint.AllowedValues.id xml_buffer, point{}.MeasurementTVP.metadata.TVPMeasurementMetadata.accuracy.Quantity.quality{}.QuantityRange.constraint.AllowedValues.extension{} xml_xml, point{}.MeasurementTVP.metadata.TVPMeasurementMetadata.accuracy.Quantity.quality{}.QuantityRange.constraint.AllowedValues.value{} xml_real64, point{}.MeasurementTVP.metadata.TVPMeasurementMetadata.accuracy.Quantity.quality{}.QuantityRange.constraint.AllowedValues.interval{} xml_buffer, point{}.MeasurementTVP.metadata.TVPMeasurementMetadata.accuracy.Quantity.quality{}.QuantityRange.constraint.AllowedValues.significantFigures xml_int64, point{}.MeasurementTVP.metadata.TVPMeasurementMetadata.accuracy.Quantity.quality{}.QuantityRange.value xml_buffer, point{}.MeasurementTVP.metadata.TVPMeasurementMetadata.accuracy.Quantity.quality{}.Category.referenceFrame xml_buffer, point{}.MeasurementTVP.metadata.TVPMeasurementMetadata.accuracy.Quantity.quality{}.Category.axisID xml_buffer, point{}.MeasurementTVP.metadata.TVPMeasurementMetadata.accuracy.Quantity.quality{}.Category.updatable xml_boolean, point{}.MeasurementTVP.metadata.TVPMeasurementMetadata.accuracy.Quantity.quality{}.Category.optional xml_boolean, point{}.MeasurementTVP.metadata.TVPMeasurementMetadata.accuracy.Quantity.quality{}.Category.definition xml_buffer, point{}.MeasurementTVP.metadata.TVPMeasurementMetadata.accuracy.Quantity.quality{}.Category.id xml_buffer, point{}.MeasurementTVP.metadata.TVPMeasurementMetadata.accuracy.Quantity.quality{}.Category.extension{} xml_xml, point{}.MeasurementTVP.metadata.TVPMeasurementMetadata.accuracy.Quantity.quality{}.Category.identifier xml_buffer, point{}.MeasurementTVP.metadata.TVPMeasurementMetadata.accuracy.Quantity.quality{}.Category.label xml_buffer, point{}.MeasurementTVP.metadata.TVPMeasurementMetadata.accuracy.Quantity.quality{}.Category.description xml_buffer, point{}.MeasurementTVP.metadata.TVPMeasurementMetadata.accuracy.Quantity.quality{}.Category.quality{} xml_xml, point{}.MeasurementTVP.metadata.TVPMeasurementMetadata.accuracy.Quantity.quality{}.Category.quality{}.xlink_href xml_buffer, point{}.MeasurementTVP.metadata.TVPMeasurementMetadata.accuracy.Quantity.quality{}.Category.quality{}.xlink_title xml_buffer, point{}.MeasurementTVP.metadata.TVPMeasurementMetadata.accuracy.Quantity.quality{}.Category.nilValues.xlink_href xml_buffer, point{}.MeasurementTVP.metadata.TVPMeasurementMetadata.accuracy.Quantity.quality{}.Category.nilValues.xlink_title xml_buffer, point{}.MeasurementTVP.metadata.TVPMeasurementMetadata.accuracy.Quantity.quality{}.Category.nilValues.NilValues.id xml_buffer, point{}.MeasurementTVP.metadata.TVPMeasurementMetadata.accuracy.Quantity.quality{}.Category.nilValues.NilValues.extension{} xml_xml, point{}.MeasurementTVP.metadata.TVPMeasurementMetadata.accuracy.Quantity.quality{}.Category.nilValues.NilValues.nilValue{} xml_buffer, point{}.MeasurementTVP.metadata.TVPMeasurementMetadata.accuracy.Quantity.quality{}.Category.nilValues.NilValues.nilValue{}.reason xml_buffer, point{}.MeasurementTVP.metadata.TVPMeasurementMetadata.accuracy.Quantity.quality{}.Category.codeSpace.xlink_href xml_buffer, point{}.MeasurementTVP.metadata.TVPMeasurementMetadata.accuracy.Quantity.quality{}.Category.codeSpace.xlink_title xml_buffer, point{}.MeasurementTVP.metadata.TVPMeasurementMetadata.accuracy.Quantity.quality{}.Category.constraint.xlink_href xml_buffer, point{}.MeasurementTVP.metadata.TVPMeasurementMetadata.accuracy.Quantity.quality{}.Category.constraint.xlink_title xml_buffer,
      point{}.MeasurementTVP.metadata.TVPMeasurementMetadata.accuracy.Quantity.quality{}.Category.constraint.AllowedTokens.id xml_buffer, point{}.MeasurementTVP.metadata.TVPMeasurementMetadata.accuracy.Quantity.quality{}.Category.constraint.AllowedTokens.extension{} xml_xml, point{}.MeasurementTVP.metadata.TVPMeasurementMetadata.accuracy.Quantity.quality{}.Category.constraint.AllowedTokens.value{} xml_buffer, point{}.MeasurementTVP.metadata.TVPMeasurementMetadata.accuracy.Quantity.quality{}.Category.constraint.AllowedTokens.pattern xml_buffer, point{}.MeasurementTVP.metadata.TVPMeasurementMetadata.accuracy.Quantity.quality{}.Category.value xml_buffer, point{}.MeasurementTVP.metadata.TVPMeasurementMetadata.accuracy.Quantity.quality{}.Text.referenceFrame xml_buffer, point{}.MeasurementTVP.metadata.TVPMeasurementMetadata.accuracy.Quantity.quality{}.Text.axisID xml_buffer, point{}.MeasurementTVP.metadata.TVPMeasurementMetadata.accuracy.Quantity.quality{}.Text.updatable xml_boolean, point{}.MeasurementTVP.metadata.TVPMeasurementMetadata.accuracy.Quantity.quality{}.Text.optional xml_boolean, point{}.MeasurementTVP.metadata.TVPMeasurementMetadata.accuracy.Quantity.quality{}.Text.definition xml_buffer, point{}.MeasurementTVP.metadata.TVPMeasurementMetadata.accuracy.Quantity.quality{}.Text.id xml_buffer, point{}.MeasurementTVP.metadata.TVPMeasurementMetadata.accuracy.Quantity.quality{}.Text.extension{} xml_xml, point{}.MeasurementTVP.metadata.TVPMeasurementMetadata.accuracy.Quantity.quality{}.Text.identifier xml_buffer, point{}.MeasurementTVP.metadata.TVPMeasurementMetadata.accuracy.Quantity.quality{}.Text.label xml_buffer, point{}.MeasurementTVP.metadata.TVPMeasurementMetadata.accuracy.Quantity.quality{}.Text.description xml_buffer, point{}.MeasurementTVP.metadata.TVPMeasurementMetadata.accuracy.Quantity.quality{}.Text.quality{} xml_xml, point{}.MeasurementTVP.metadata.TVPMeasurementMetadata.accuracy.Quantity.quality{}.Text.quality{}.xlink_href xml_buffer, point{}.MeasurementTVP.metadata.TVPMeasurementMetadata.accuracy.Quantity.quality{}.Text.quality{}.xlink_title xml_buffer, point{}.MeasurementTVP.metadata.TVPMeasurementMetadata.accuracy.Quantity.quality{}.Text.nilValues.xlink_href xml_buffer, point{}.MeasurementTVP.metadata.TVPMeasurementMetadata.accuracy.Quantity.quality{}.Text.nilValues.xlink_title xml_buffer, point{}.MeasurementTVP.metadata.TVPMeasurementMetadata.accuracy.Quantity.quality{}.Text.nilValues.NilValues.id xml_buffer, point{}.MeasurementTVP.metadata.TVPMeasurementMetadata.accuracy.Quantity.quality{}.Text.nilValues.NilValues.extension{} xml_xml, point{}.MeasurementTVP.metadata.TVPMeasurementMetadata.accuracy.Quantity.quality{}.Text.nilValues.NilValues.nilValue{} xml_buffer, point{}.MeasurementTVP.metadata.TVPMeasurementMetadata.accuracy.Quantity.quality{}.Text.nilValues.NilValues.nilValue{}.reason xml_buffer, point{}.MeasurementTVP.metadata.TVPMeasurementMetadata.accuracy.Quantity.quality{}.Text.constraint.xlink_href xml_buffer, point{}.MeasurementTVP.metadata.TVPMeasurementMetadata.accuracy.Quantity.quality{}.Text.constraint.xlink_title xml_buffer, point{}.MeasurementTVP.metadata.TVPMeasurementMetadata.accuracy.Quantity.quality{}.Text.constraint.AllowedTokens.id xml_buffer, point{}.MeasurementTVP.metadata.TVPMeasurementMetadata.accuracy.Quantity.quality{}.Text.constraint.AllowedTokens.extension{} xml_xml, point{}.MeasurementTVP.metadata.TVPMeasurementMetadata.accuracy.Quantity.quality{}.Text.constraint.AllowedTokens.value{} xml_buffer, point{}.MeasurementTVP.metadata.TVPMeasurementMetadata.accuracy.Quantity.quality{}.Text.constraint.AllowedTokens.pattern xml_buffer,
      point{}.MeasurementTVP.metadata.TVPMeasurementMetadata.accuracy.Quantity.quality{}.Text.value xml_buffer, point{}.MeasurementTVP.metadata.TVPMeasurementMetadata.accuracy.Quantity.nilValues.xlink_href xml_buffer, point{}.MeasurementTVP.metadata.TVPMeasurementMetadata.accuracy.Quantity.nilValues.xlink_title xml_buffer, point{}.MeasurementTVP.metadata.TVPMeasurementMetadata.accuracy.Quantity.nilValues.NilValues.id xml_buffer, point{}.MeasurementTVP.metadata.TVPMeasurementMetadata.accuracy.Quantity.nilValues.NilValues.extension{} xml_xml, point{}.MeasurementTVP.metadata.TVPMeasurementMetadata.accuracy.Quantity.nilValues.NilValues.nilValue{} xml_buffer, point{}.MeasurementTVP.metadata.TVPMeasurementMetadata.accuracy.Quantity.nilValues.NilValues.nilValue{}.reason xml_buffer, point{}.MeasurementTVP.metadata.TVPMeasurementMetadata.accuracy.Quantity.uom.code xml_buffer, point{}.MeasurementTVP.metadata.TVPMeasurementMetadata.accuracy.Quantity.uom.xlink_href xml_buffer, point{}.MeasurementTVP.metadata.TVPMeasurementMetadata.accuracy.Quantity.uom.xlink_title xml_buffer, point{}.MeasurementTVP.metadata.TVPMeasurementMetadata.accuracy.Quantity.constraint.xlink_href xml_buffer, point{}.MeasurementTVP.metadata.TVPMeasurementMetadata.accuracy.Quantity.constraint.xlink_title xml_buffer, point{}.MeasurementTVP.metadata.TVPMeasurementMetadata.accuracy.Quantity.constraint.AllowedValues.id xml_buffer, point{}.MeasurementTVP.metadata.TVPMeasurementMetadata.accuracy.Quantity.constraint.AllowedValues.extension{} xml_xml, point{}.MeasurementTVP.metadata.TVPMeasurementMetadata.accuracy.Quantity.constraint.AllowedValues.value{} xml_real64, point{}.MeasurementTVP.metadata.TVPMeasurementMetadata.accuracy.Quantity.constraint.AllowedValues.interval{} xml_buffer, point{}.MeasurementTVP.metadata.TVPMeasurementMetadata.accuracy.Quantity.constraint.AllowedValues.significantFigures xml_int64, point{}.MeasurementTVP.metadata.TVPMeasurementMetadata.accuracy.Quantity.value xml_real64, point{}.MeasurementTVP.metadata.TVPMeasurementMetadata.aggregationDuration xml_buffer
    -> ListExploder
ListExploder
    ATTR_ACCUM_MODE = Merge List Attributes
    ATTR_CONFLICT_RES = Use List Attribute Values
    INDEX_ATTR = _element_index
    LIST_ATTR = point{}
    ELEMENTS -> Sampler
Sampler
    GROUP_BY = gml_parent_id
    RATE = 1
    SAMPLE_MODE = No
    SAMPLE_TYPE_LONG = Last N Features
    SAMPLED -> SubstringExtractor_2
SubstringExtractor_2
    END = 15
    RESULT_ATTR = stationID
    SRC_STRING = @Value(gml_id)
    START = 8
    -> AttributeManager_2
AttributeManager_2
    ATTR_TABLE:
      RENAME_SET_VALUE MeasurementTVP.time > time
      RENAME_SET_VALUE MeasurementTVP.value > flow
      REMOVE gml_parent_property
      REMOVE gml_id
      REMOVE _element_index
      RENAME_SET_VALUE stationID > gauge_id
    -> FeatureJoiner [RIGHT]
MonitoringPoint (reader GML_1)
    attributes: type.owns xml_boolean, type.nilReason xml_buffer, type.gml_remoteSchema xml_buffer, type.xlink_href xml_buffer, type.xlink_title xml_buffer, sampledFeature.owns xml_boolean, sampledFeature.nilReason xml_buffer, sampledFeature.gml_remoteSchema xml_buffer, sampledFeature.xlink_href xml_buffer, sampledFeature.xlink_title xml_buffer, sampledFeature.xsi_nil xml_boolean, lineage xml_xml, lineage.nilReason xml_buffer, lineage.uuidref xml_buffer, lineage.xlink_href xml_buffer, lineage.xlink_title xml_buffer, relatedObservation{}.nilReason xml_buffer, relatedObservation{}.gml_remoteSchema xml_buffer, relatedObservation{}.xlink_href xml_buffer, relatedObservation{}.xlink_title xml_buffer, relatedSamplingFeature{}.SamplingFeatureComplex.role.owns xml_boolean, relatedSamplingFeature{}.SamplingFeatureComplex.role.nilReason xml_buffer, relatedSamplingFeature{}.SamplingFeatureComplex.role.gml_remoteSchema xml_buffer, relatedSamplingFeature{}.SamplingFeatureComplex.role.xlink_href xml_buffer, relatedSamplingFeature{}.SamplingFeatureComplex.role.xlink_title xml_buffer, relatedSamplingFeature{}.SamplingFeatureComplex.relatedSamplingFeature.nilReason xml_buffer, relatedSamplingFeature{}.SamplingFeatureComplex.relatedSamplingFeature.gml_remoteSchema xml_buffer, relatedSamplingFeature{}.SamplingFeatureComplex.relatedSamplingFeature.xlink_href xml_buffer, relatedSamplingFeature{}.SamplingFeatureComplex.relatedSamplingFeature.xlink_title xml_buffer, parameter{}.nilReason xml_buffer,
      parameter{}.gml_remoteSchema xml_buffer, parameter{}.xlink_href xml_buffer, parameter{}.xlink_title xml_buffer, parameter{}.NamedValue.name.owns xml_boolean, parameter{}.NamedValue.name.nilReason xml_buffer, parameter{}.NamedValue.name.gml_remoteSchema xml_buffer, parameter{}.NamedValue.name.xlink_href xml_buffer, parameter{}.NamedValue.name.xlink_title xml_buffer, parameter{}.NamedValue.value xml_xml, hostedProcedure{} xml_xml, hostedProcedure{}.nilReason xml_buffer, hostedProcedure{}.gml_remoteSchema xml_buffer, hostedProcedure{}.xlink_href xml_buffer, hostedProcedure{}.xlink_title xml_buffer, positionalAccuracy{} xml_xml, positionalAccuracy{}.nilReason xml_buffer, positionalAccuracy{}.uuidref xml_buffer, positionalAccuracy{}.xlink_href xml_buffer, positionalAccuracy{}.xlink_title xml_buffer, shape xml_geometry, relatedParty{} xml_xml, relatedParty{}.nilReason xml_buffer, relatedParty{}.uuidref xml_buffer, relatedParty{}.xlink_href xml_buffer, relatedParty{}.xlink_title xml_buffer, monitoringType{}.owns xml_boolean, monitoringType{}.nilReason xml_buffer, monitoringType{}.gml_remoteSchema xml_buffer, monitoringType{}.xlink_href xml_buffer, monitoringType{}.xlink_title xml_buffer,
      descriptionReference{}.owns xml_boolean, descriptionReference{}.nilReason xml_buffer, descriptionReference{}.gml_remoteSchema xml_buffer, descriptionReference{}.xlink_href xml_buffer, descriptionReference{}.xlink_title xml_buffer, verticalDatum{} xml_xml, verticalDatum{}.nilReason xml_buffer, verticalDatum{}.gml_remoteSchema xml_buffer, verticalDatum{}.xlink_href xml_buffer, verticalDatum{}.xlink_title xml_buffer, timeZone.owns xml_boolean, timeZone.TimeZone.zoneOffset xml_buffer, timeZone.TimeZone.zoneAbbreviation xml_buffer, daylightSavingTimeZone.owns xml_boolean, daylightSavingTimeZone.TimeZone.zoneOffset xml_buffer, daylightSavingTimeZone.TimeZone.zoneAbbreviation xml_buffer
    -> AttributeManager
AttributeManager
    ATTR_TABLE:
      RENAME_SET_VALUE sampledFeature.xlink_title > gnisname
      REMOVE gml_parent_property
      REMOVE gml_id
      SET_TO gauge_id = @Value(gml_parent_id)
    -> SubstringExtractor
SubstringExtractor
    END = 16
    RESULT_ATTR = gauge_id
    SRC_STRING = @Value(gauge_id)
    START = 9
    -> FeatureJoiner [LEFT]
FeatureJoiner
    ATTR_CONFLICT_RES = Use Right
    GEOMETRY_HANDLING = Use Left
    JOIN_KEYS = gml_parent_id gml_parent_id AUTO
    JOIN_MODE = Inner
    JOINED -> AttributeManager_5
    JOINED -> AttributeManager_3
AttributeManager_3
    ATTR_TABLE:
      SET_TO id = @Value(gauge_id)_@Value(gnisname)
      SET_TO datasource = USGS
      SET_TO url = https://waterdata.usgs.gov/nwis/uv?@Value(gauge_id)
    -> AttributeManager_4
AttributeManager_4
    ATTR_TABLE:
      REMOVE time
      REMOVE flow
      REMOVE gauge_id
      RENAME_SET_VALUE gnisname > name
      SET_TO watershed = $(watershed)
    -> DuplicateFilter
DuplicateFilter
    INPUT_ORDERED_CHOICE = No
    KEYATTR = datasource name url watershed id
    UNIQUE -> UpdateDetector [Revised]
AttributeManager_5
    ATTR_TABLE:
      RENAME_SET_VALUE time > measure_time
      RENAME_SET_VALUE flow > value
      SET_TO id = @Value(gauge_id)_@Value(gnisname)
    -> AttributeManager_6
AttributeManager_6
    ATTR_TABLE:
      SET_TO value = @int(@Value(value))
      REMOVE gauge_id
      REMOVE gnisname
      RENAME_SET_VALUE id > gauge
    -> AttributeRangeFilter
AttributeRangeFilter
    IN_ATTR = value
    LUT = 0,,positive
    positive -> UpdateDetector_2 [Revised]
data (reader POSTGRES_1)
    attributes: id serial,PrimaryKey, value int4, measure_time timestamptz, gauge varchar(100)
    -> UpdateDetector_2 [Original]
Note: Currently only storing the most recent value
UpdateDetector_2
    BLANK_AND_MISSING_DIFFER = No
    EXTRA_VERTEX_TOLERANCE = 0
    KEYATTR = gauge
    LENIENT_MATCH = no
    MATCH = NONE
    MATCHATTRS = measure_time value gauge
    Updated -> data (writer POSTGRES_2)
    Inserted -> data (writer POSTGRES_2)
data (writer POSTGRES_2)
    attributes: id serial,PrimaryKey, value int4, measure_time timestamptz, gauge varchar(100)
gauge (reader POSTGIS_1)
    attributes: watersource int4,BTree, datasource varchar(10),BTree, name varchar(100), url varchar(80), watersourcename varchar(80), id varchar(100),PrimaryKey, watershed char(2)
    -> UpdateDetector [Original]
UpdateDetector
    BLANK_AND_MISSING_DIFFER = No
    EXTRA_VERTEX_TOLERANCE = 0
    KEYATTR = id
    LENIENT_MATCH = no
    MATCH = 2D
    MATCHATTRS = id watershed url name
    Updated -> Logger
    Inserted -> Logger
Logger
    LOG_FEATURE = LOG_ONLY
    MAXCOORDS = 20
    MAXFEATS = 20
    MESSAGE = Found a new gauge: @Value(name)
    SEVERITY = INFO
    LOGGED -> gauge (writer POSTGIS_2)
gauge (writer POSTGIS_2)
    attributes: datasource varchar(10),BTree, name varchar(100), url varchar(80), id varchar(100),PrimaryKey, watershed char(2)

FME custom transformer UpdateDetector
This transformer is based on the ChangeDetector and extends its functionality by adding an Updated output port. It detects changes between two sets of input features.
One set of features enters the transformer via the Original port. The other set enters via the Revised port. Both sets must have a key attribute, which will be used to compare them against each other.
An Original feature is output via the Unchanged port when it is found to have matching key attribute and either matching geometry, matching attribute values, or both, with a feature in the Revised set.
An Original feature is output via the Deleted port when no key attribute match for it can be found in the Revised set.
A Revised feature with no key attribute match in the Original set is output via the Inserted port.
A Revised feature with key attribute match in the Original set and has changes either in geometry, or attribute values, or both, is output via the Updated port.
Inserted, updated and deleted features will have fme_db_operation set to INSERT, UPDATE or DELETE respectively.
Please note that to get correct results, the key attribute must be provided to both "Key Attribute" and "Attribute(s) to match" parameter prompts. 
Connect the transformer in your workspace and set the required parameters.
If Lenient Geometry Matching is set to yes then the order of points in line and area features will be ignored.
If Treat Blank Value as Different From Missing Attribute is Yes, then an attribute will be considered different for two features when one feature contains the attribute with a blank value and the other feature does not contain the attribute at all.
When geometry is being matched, Extra Vertex Tolerance can allow for extra vertices along line segments. A value of 0 means that no such extra vertices are permitted. A nonzero value controls how close any extra vertices must be to the line connecting the adjoining matching vertices. Note: This setting has no effect when using lenient geometry matching.

Parameters:
- KEYATTR =   # " " Key Attribute
- MATCH = 2D   # Match Geometry
- LENIENT_MATCH = no   # Lenient Geometry Matching
- MATCHATTRS =   # " " Attributes to Match
- BLANK_AND_MISSING_DIFFER = No   # Treat Blank Value as Different From Missing Attribute
- EXTRA_VERTEX_TOLERANCE = 0   # Extra Vertex Tolerance (optional)

Original (input)
    -> ATTRIBUTECREATOR
Note: Created by Dmitri Bagh / February 03, 2006 / dmitri.bagh@safe.com
Revised (input)
    -> ATTRIBUTECREATOR_2
Note: All parameters / are published / to match functionality / of ChangeDetector
Note: UPDATEDETECTOR
ChangeDetector
    BLANK_AND_MISSING_DIFFER = $(BLANK_AND_MISSING_DIFFER)
    EXTRA_VERTEX_TOLERANCE = $(EXTRA_VERTEX_TOLERANCE)
    LENIENT_MATCH = $(LENIENT_MATCH)
    MATCH = $(MATCH)
    MATCHATTRS = $(MATCHATTRS)
    MATCH_STRATEGY = Match Selected Attributes
    UNCHANGED -> ATTRIBUTEREMOVER_3
    ADDED -> Matcher_2
    DELETED -> Matcher
Updated (output)
Inserted (output)
Unchanged (output)
Deleted (output)

Bookmark: OrigFlag Creators
  Assigning OrigFlag Y for original 
  features and N for revised.
  For further use in testers 
  after Matcher 
  where original and revised 
  feaures can be merged together.
ATTRIBUTECREATOR: AttributeCreator
    ATTR_TABLE = SET_TO OrigFlag = Y
    -> ChangeDetector [ORIGINAL]
    -> Matcher_2
ATTRIBUTECREATOR_2: AttributeCreator
    ATTR_TABLE = SET_TO OrigFlag = N
    -> ChangeDetector [REVISED]
    -> Matcher

Bookmark: Matchers
  Here published Key Attribute
  distinguishes between added 
  and modified (above), 
  and - between deleted 
  and modified (below)
Matcher_2
    BLANK_AND_MISSING_DIFFER = No
    CNT_ATTR = _match_id
    DIFFATTRS = OrigFlag
    LENIENT_MATCH = No
    MATCH = NONE
    MATCHATTRS = $(KEYATTR)
    MATCH_STRATEGY = Match Selected Attributes
    MATCHED -> TESTER
    NOT_MATCHED -> TESTER_2
Matcher
    BLANK_AND_MISSING_DIFFER = No
    CNT_ATTR = _match_id
    DIFFATTRS = OrigFlag
    LENIENT_MATCH = No
    MATCH = NONE
    MATCHATTRS = $(KEYATTR)
    MATCH_STRATEGY = Match Selected Attributes
    NOT_MATCHED -> TESTER_3

Bookmark: Testers
  For updated and added 
  we keep revised features
  For deleted - original features
TESTER: Tester
    BOOL_OP = OR
    TEST_CLAUSE = TEST @Value(OrigFlag) = N
    PASSED -> ATTRIBUTEREMOVER
TESTER_2: Tester
    BOOL_OP = OR
    TEST_CLAUSE = TEST @Value(OrigFlag) = N
    PASSED -> ATTRIBUTEREMOVER_2
TESTER_3: Tester
    BOOL_OP = OR
    TEST_CLAUSE = TEST @Value(OrigFlag) = Y
    PASSED -> ATTRIBUTEREMOVER_4

Bookmark: Deleting temp attributes
ATTRIBUTEREMOVER: AttributeRemover
    REMOVE_ATTRS = _match_id,OrigFlag
    -> AttributeCreator
ATTRIBUTEREMOVER_2: AttributeRemover
    REMOVE_ATTRS = _match_id,OrigFlag
    -> AttributeCreator_2
ATTRIBUTEREMOVER_3: AttributeRemover
    REMOVE_ATTRS = OrigFlag
    -> Unchanged (output)
ATTRIBUTEREMOVER_4: AttributeRemover
    REMOVE_ATTRS = _match_id,OrigFlag
    -> AttributeCreator_3

Bookmark: Add fme_db_operation attribute
AttributeCreator
    ATTR_TABLE = SET_TO fme_db_operation = UPDATE
    -> Updated (output)
AttributeCreator_2
    ATTR_TABLE = SET_TO fme_db_operation = INSERT
    -> Inserted (output)
AttributeCreator_3
    ATTR_TABLE = SET_TO fme_db_operation = DELETE
    -> Deleted (output)
